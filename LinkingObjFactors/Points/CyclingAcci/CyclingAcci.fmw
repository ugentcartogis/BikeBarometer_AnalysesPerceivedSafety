FME workspace CyclingAcci.fmw

Parameters:
- SourceDataset_SHAPEFILE_3 = C:\Users\Sien Benoit\OneDrive - UGent\Werk_UGent\Doctoraat\Datasets_routes\DataFietsbarometerVL_210402\06_LinkingObjFactors\Points\dataset_points_210402_08.shp   # Source Esri Shapefile(s)
- SourceDataset_SHAPEFILE = C:\Users\Sien Benoit\OneDrive - UGent\Werk_UGent\Doctoraat\Datasets_environment\cyclingaccidents\MOW\CyclingAccidents_2017-2019_projected.shp   # Source Esri Shapefile(s)
- DestDataset_CSV2 = C:\Users\Sien Benoit\OneDrive - UGent\Werk_UGent\Doctoraat\Datasets_routes\DataFietsbarometerVL_210402\06_LinkingObjFactors\Points\CyclingAcci   # Destination CSV (Comma Separated Value) Folder

Readers:
- SHAPEFILE_1: SHAPEFILE from $(SourceDataset_SHAPEFILE_3)
- SHAPEFILE_2: SHAPEFILE from $(SourceDataset_SHAPEFILE)

Writers:
- CSV2_1: CSV2 to $(DestDataset_CSV2)

Note: Cycling accidents that occurred in the period 2017 - 2019 in Flanders.
Note: Create a buffer of 10 m around every assessed intersection.
Note: Find and count all points that are in the buffer of a node.
Note: Select the necessary attributes and write to a csv file that can be joined to the original points shapefile.
CyclingAccidents_2017-2019_projected (reader SHAPEFILE_2)
    attributes: gemeente char(254), totaalBetr long, totaalZwaa long, totaalLich long, aantalDode long, locatie_1 char(254), kmp_1 double, locatie_2 char(254), kmp_2 double
    -> PointOnAreaOverlayer [POINT]
Note: Points dataset that needs additional new attributes
dataset_points_210402_08 (reader SHAPEFILE_1)
    attributes: node_id long
    -> Bufferer

Bookmark: Buffer the intersections
Bufferer
    ANGLE = 22.5
    CAP_STYLE = Round
    CORNER_STYLE = Round
    MODE = AREA
    OFFSET = 25
    OFFSET_UNITS = NONE
    BUFFERED -> PointOnAreaOverlayer [AREA]

Bookmark: Find points in the buffers
PointOnAreaOverlayer
    DEAGGREGATE_INPUT = Yes
    OV_ATTR = _overlaps
    POLYS_FIRST = NO
    AREA -> AttributeManager

Bookmark: Write to csv
AttributeManager
    ATTR_TABLE = RENAME_SET_VALUE _overlaps > CyclingAcci
    -> CyclingAcci (writer CSV2_1)
CyclingAcci (writer CSV2_1)
    attributes: node_id string, CyclingAcci string
