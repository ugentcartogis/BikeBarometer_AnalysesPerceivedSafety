FME workspace TrafficVolume.fmw

Parameters:
- SourceDataset_SHAPEFILE = C:\Users\Sien Benoit\OneDrive - UGent\Werk_UGent\Doctoraat\Datasets_environment\trafficvolume\TomTom - Move\network_projected_trafficdata.shp   # Source Esri Shapefile(s)
- SourceDataset_SHAPEFILE_3 = C:\Users\Sien Benoit\OneDrive - UGent\Werk_UGent\Doctoraat\Datasets_routes\DataFietsbarometerVL_210402\06_LinkingObjFactors\Points\dataset_points_210402_08.shp   # Source Esri Shapefile(s)
- DestDataset_CSV2 = C:\Users\Sien Benoit\OneDrive - UGent\Werk_UGent\Doctoraat\Datasets_routes\DataFietsbarometerVL_210402\06_LinkingObjFactors\Points\TrafficVolume   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: TomTom segments that provide new attributes. / Duplicate segments must not be deleted, because we want to include the data of all directions.
Note: Find all lines that are in the buffer of a node.
Note: Calculate the sum of the number of vehicles along the lines in the buffer. Divide by 2 because every vehicles goes from one segment to another at an intersection and would be counted double otherwise.
Note: Write to a csv file that can be joined to the original points shapefile.
network_projected_trafficdata (reader SHAPEFILE_1)
    attributes: Id number(19,0), Segment_Id char(20), NewSegId char(40), Length double, FRC number(19,0), SpeedLimit number(19,0), StreetName char(100), BS_AvgTt double, BS_MedTt double, BS_ratio double, BS_AvgSp double, BS_HvgSp double, BS_MedSp double, BS_SdSp double, BS_Hits number(20,0), BS_P5sp number(20,0), BS_P10sp number(20,0), BS_P15sp number(20,0), BS_P20sp number(20,0), BS_P25sp number(20,0), BS_P30sp number(20,0), BS_P35sp number(20,0), BS_P40sp number(20,0), BS_P45sp number(20,0), BS_P50sp number(20,0), BS_P55sp number(20,0), BS_P60sp number(20,0), BS_P65sp number(20,0), BS_P70sp number(20,0), BS_P75sp number(20,0),
      BS_P80sp number(20,0), BS_P85sp number(20,0), BS_P90sp number(20,0), BS_P95sp number(20,0)
    -> LineOnAreaOverlayer [LINE]
Note: Points dataset that needs additional new attributes
Note: Create a buffer of 10 m around every assessed intersection.
dataset_points_210402_08 (reader SHAPEFILE_2)
    attributes: node_id long
    -> Bufferer

Bookmark: Buffer the intersections
Bufferer
    ANGLE = 22.5
    CAP_STYLE = Round
    CORNER_STYLE = Round
    MODE = AREA
    OFFSET = 10
    OFFSET_UNITS = NONE
    BUFFERED -> LineOnAreaOverlayer [AREA]

Bookmark: Find lines in the buffers
LineOnAreaOverlayer
    CANDIDATE_LIST_ATTRS_TO_INCLUDE = BS_Hits Id
    CANDIDATE_LIST_ATTRS_TO_INCLUDE_MODE = Selected Attributes
    CANDIDATE_LIST_NAME = network_id
    CLEANING_TOLERANCE = Automatic
    DEAGGREGATE_INPUT = Yes
    OV_ATTR = _overlaps
    AREA -> ListStatisticsCalculator

Bookmark: Sum the number of vehicles at the intersection
ListStatisticsCalculator
    LIST_ATTR = network_id{}.BS_Hits
    PREFIX = stats_
    -> AttributeManager
AttributeManager
    ATTR_TABLE:
      REMOVE network_id{}.Id
      REMOVE network_id{}.BS_Hits
      REMOVE _overlaps
      REMOVE stats_min
      REMOVE stats_max
      REMOVE stats_median
      REMOVE stats_count
      RENAME_SET_VALUE stats_sum > TrafficVolume = @div(@Value(TrafficVolume),2)
      REMOVE stats_range
      REMOVE stats_mean
      REMOVE stats_stdev
      REMOVE stats_stdevp
      REMOVE stats_mode
    -> TrafficVolume (writer CSV2_1)

Bookmark: Write to csv
TrafficVolume (writer CSV2_1)
    attributes: node_id string, TrafficVolume string

FME custom transformer ListStatisticsCalculator
Calculates fundamental statistics of element values in the specified list, and adds attributes storing the calculation results to the feature.
    Only decimal numbers can be accepted as the list elements. 0 at the head of an element will be ignored. 
    If the incoming feature does not have list attribute with the specified name, or the list contains one or more non-numeric elements, then the feature will be output from the 
    <Rejected>
    port.
    Every rejected feature will have an attribute named "_liststats_error", which contains a text describing the rejected reason. 
    This transformer contains a Python script, which was tested with both Python 2.7 interpreter and 3.6 interpreter.
Parameters
    List Attribute
    :
    Specify a list name which contains numeric elements.
    Prefix of Statistics Attributes
    :
    Specify a common prefix which should be added to names of result attributes. This can be set to empty string, if unnecessary.
    Output features will have these attributes if you specify "stats_" to this parameter.
    -----
    stats_min - The minimum value in all the values. 
    stats_max - The maximum value in all the values. 
    stats_median - The middle value of all the values. 
    stats_count - The number of the elements. 
    stats_sum - The sum of all the values. 
    stats_range - The difference between the minimum and the maximum. i.e. equals to the maximum minus the minimum. 
    stats_mean - The average of all the values. 
    stats_stdev - The standard deviation (sample) of all the values. This will be empty if the number of elements is equal to 1.
    stats_stdevp - The standard deviation (population) of all the values. 
    stats_mode - The most frequent of all the values. If two or more values occur with the highest frequency, one of them will be returned randomly. 
    -----

Parameters:
- LIST_ATTR =   # " " List Attribute
- PREFIX = stats_   # TYPE:varchar(200) Prefix of Statistics Attributes

Input (input)
    -> ParameterFetcher
ParameterFetcher
    ATTR_LIST = liststatisticscalculator.list_attr {$(LIST_ATTR)}
    -> PythonCaller
PythonCaller
    NEW_ATTRIBUTES = min.liststatisticscalculator max.liststatisticscalculator median.liststatisticscalculator count.liststatisticscalculator sum.liststatisticscalculator range.liststatisticscalculator mean.liststatisticscalculator stdev.liststatisticscalculator stdevp.liststatisticscalculator mode.liststatisticscalculator liststatisticscalculator.histogram{}.count liststatisticscalculator.histogram{}.value liststatisticscalculator.flag
    PYTHONSOURCE:
      # 2018-06-14, Takashi Iijime, Updated to support Python 3.x interpreter.
      # 2016-06-24, Takashi Iijima, Added stdevp - standard deviation (population).
      # 2014-08-02, Takashi Iijima, Original Implementation

      import fmeobjects, locale, re, math

      class ListStatisticsCalculator(object):
          def __init__(self):
              import platform
              if platform.python_version_tuple()[0] == '2':
                  loc = locale.getdefaultlocale()
                  enc = loc[1] if loc else 'utf_8'
                  self.toStr = lambda s: s.encode(enc) if isinstance(s, unicode) else s
              else:
                  self.toStr = lambda s: s

          def input(self, feature):
              try:
                  listName = self.toStr(feature.getAttribute('liststatisticscalculator.list_attr'))
                  m = re.match(r'^(.+)\{\}(.*)$', listName)

                  front, index, back = m.group(1), 0, m.group(2)
                  values, total, histogram = [], 0.0, {}
                  while True:
                      v = feature.getAttribute('%s{%d}%s' % (front, index, back))
                      if v == None:
                          break
                      v = float(v)
                      values.append(v)
                      total += v
                      histogram[v] = histogram.setdefault(v, 0) + 1
                      index += 1

                  # Number of elements.
                  count = len(values)
                  if count < 1:
                      raise Exception('could not find valid element')
                  values.sort() # ascending sort

                  # Calculate median, average (mean) and standard deviation.
                  mid = count // 2
                  median = values[mid] if count % 2 else 0.5 * (values[mid - 1] + values[mid])
                  avrg = total / count
                  s = sum([(v - avrg)**2 for v in values])
                  stdev = math.sqrt(s / (count - 1)) if 1 < count else ''
                  stdevp = math.sqrt(s / count)

                  # Find mode.
                  mode, num = None, 0
                  for i, v in enumerate(sorted(histogram.keys())):
                      n = histogram[v]
                      if num < n:
                          mode, num = v, n
                      # Reserved: Set histogram elements
                      #feature.setAttribute('liststatisticscalculator.histogram{%d}.count' % i, n)
                      #feature.setAttribute('liststatisticscalculator.histogram{%d}.value' % i, v)

                  # Set statistics attributes.
                  feature.setAttribute('min.liststatisticscalculator', values[0])
                  feature.setAttribute('max.liststatisticscalculator', values[-1])
                  feature.setAttribute('median.liststatisticscalculator', median)
                  feature.setAttribute('count.liststatisticscalculator', count)
                  feature.setAttribute('sum.liststatisticscalculator', total)
                  feature.setAttribute('range.liststatisticscalculator', values[-1] - values[0])
                  feature.setAttribute('mean.liststatisticscalculator', avrg)
                  feature.setAttribute('stdev.liststatisticscalculator', stdev)
                  feature.setAttribute('stdevp.liststatisticscalculator', stdevp)
                  feature.setAttribute('mode.liststatisticscalculator', mode)

                  # Set flag.
                  feature.setAttribute('liststatisticscalculator.flag', 1)

              except Exception as ex:
                  feature.setAttribute('_liststats_error', '%s' % ex)
                  feature.setAttribute('liststatisticscalculator.flag', 0)

              self.pyoutput(feature)
    PYTHONSYMBOL = ListStatisticsCalculator
    -> Tester
Tester
    BOOL_OP = OR
    TEST_CLAUSE = TEST @Value(liststatisticscalculator.flag) = 1
    TEST_MODE = Automatic
    PASSED -> BulkAttributeRenamer
    FAILED -> BulkAttributeRemover_2
Note: Add common prefix
BulkAttributeRenamer
    ATTRCHOICE = Selected Attributes
    ATTRLIST = min.liststatisticscalculator max.liststatisticscalculator median.liststatisticscalculator count.liststatisticscalculator sum.liststatisticscalculator range.liststatisticscalculator mean.liststatisticscalculator stdev.liststatisticscalculator stdevp.liststatisticscalculator mode.liststatisticscalculator
    PATTERN_ACTION_DISP = Add String Prefix
    REPLACE_STR = $(PREFIX)
    -> BulkAttributeRenamer_2
Note: Remove extra suffix
BulkAttributeRenamer_2
    ATTRCHOICE = All Attributes
    CASE_DISP = yes
    PATTERN_ACTION_DISP = Remove Suffix String
    REPLACE_STR = .liststatisticscalculator
    -> BulkAttributeRemover
Note: Remove unnecessary attributes
BulkAttributeRemover
    ATTR_EXP = ^liststatisticscalculator
    -> Output (output)
Output (output)
BulkAttributeRemover_2
    ATTR_EXP = liststatisticscalculator
    -> AttributeExposer
Note: AttributeExposer [AttributeExposer] / Attributes To Expose: _liststats_error
AttributeExposer
    ATTR_LIST = _liststats_error
    -> <Rejected> (output)
<Rejected> (output)
