FME workspace CyclingInfra.fmw

Parameters:
- SourceDataset_SHAPEFILE_3 = C:\Users\Sien Benoit\OneDrive - UGent\Werk_UGent\Doctoraat\Datasets_routes\DataFietsbarometerVL_210402\06_LinkingObjFactors\Points\dataset_points_210402_08.shp   # Source Esri Shapefile(s)
- SourceDataset_SHAPEFILE = C:\Users\Sien Benoit\OneDrive - UGent\Werk_UGent\Doctoraat\Datasets_environment\cyclinginfra\dataset_segments_210402_08_infra.shp   # Source Esri Shapefile(s)
- DestDataset_CSV2 = C:\Users\Sien Benoit\OneDrive - UGent\Werk_UGent\Doctoraat\Datasets_routes\DataFietsbarometerVL_210402\06_LinkingObjFactors\Points\CyclingInfra   # Destination CSV (Comma Separated Value) Folder

Readers:
- SHAPEFILE_1: SHAPEFILE from $(SourceDataset_SHAPEFILE_3)
- SHAPEFILE_2: SHAPEFILE from $(SourceDataset_SHAPEFILE)

Writers:
- CSV2_1: CSV2 to $(DestDataset_CSV2)

Note: Segments dataset with the most assigned cycling infrastructure type per segment
Note: Find all lines that are in the buffer of a node.
Note: Find the most occurring cycling infrastructure along the lines in the buffer.
Note: Select the necessary attributes and write to a csv file that can be joined to the original points shapefile.
dataset_segments_210402_08_infra (reader SHAPEFILE_2)
    attributes: segment_id long, mode char(254)
    -> LineOnAreaOverlayer [LINE]
Note: Points dataset that needs additional new attributes
Note: Create a buffer of 10 m around every assessed intersection.
dataset_points_210402_08 (reader SHAPEFILE_1)
    attributes: node_id long
    -> Bufferer

Bookmark: Buffer the intersections
Bufferer
    ANGLE = 22.5
    CAP_STYLE = Round
    CORNER_STYLE = Round
    MODE = AREA
    OFFSET = 10
    OFFSET_UNITS = NONE
    BUFFERED -> LineOnAreaOverlayer [AREA]

Bookmark: Find lines in the buffers
LineOnAreaOverlayer
    CANDIDATE_LIST_ATTRS_TO_INCLUDE = mode
    CANDIDATE_LIST_ATTRS_TO_INCLUDE_MODE = Selected Attributes
    CANDIDATE_LIST_NAME = fietsbarometer_
    CLEANING_TOLERANCE = Automatic
    DEAGGREGATE_INPUT = Yes
    OV_ATTR = _overlaps
    AREA -> ListHistogrammer

Bookmark: Find the cycling infrastructure at the intersection
ListHistogrammer
    LIST_NAME = _histogram
    SRC_LIST = fietsbarometer_{}.mode
    -> AttributeCreator
AttributeCreator
    ATTR_TABLE = SET_TO CyclingInfra = FME_CONDITIONAL:DEFAULT_VALUE'no infrastructure found'BOOL_OP;OR;COMPOSITE_TEST;1;TEST @Value(_histogram{0}.count) > @Value(_histogram{1}.count)'@Value(_histogram{0}.value)'BOOL_OP;OR;COMPOSITE_TEST;1;TEST @Value(_histogram{1}.count) > @Value(_histogram{2}.count)'@Value(_histogram{1}.value)'BOOL_OP;OR;COMPOSITE_TEST;1;TEST @Value(_histogram{2}.count) > @Value(_histogram{3}.count)'@Value(_histogram{2}.value)'BOOL_OP;OR;COMPOSITE_TEST;1;TEST @Value(_histogram{3}.count) > @Value(_histogram{0}.count)'@Value(_histogram{3}.value)'FME_NUM_CONDITIONS5___
    -> AttributeManager

Bookmark: Write to csv
AttributeManager
    ATTR_TABLE:
      REMOVE _overlaps
      REMOVE fietsbarometer_{}.mode
      REMOVE _histogram{}.count
      REMOVE _histogram{}.value
    -> CyclingInfra (writer CSV2_1)
CyclingInfra (writer CSV2_1)
    attributes: node_id string, CyclingInfra string
