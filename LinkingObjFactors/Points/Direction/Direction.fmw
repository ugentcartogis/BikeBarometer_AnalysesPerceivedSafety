FME workspace Direction.fmw

Parameters:
- SourceDataset_SHAPEFILE = C:\Users\Sien Benoit\OneDrive - UGent\Werk_UGent\Doctoraat\Datasets_environment\directionroute\routesegments_2020_2021.shp   # Source Esri Shapefile(s)
- SourceDataset_SHAPEFILE_3 = C:\Users\Sien Benoit\OneDrive - UGent\Werk_UGent\Doctoraat\Datasets_routes\DataFietsbarometerVL_210402\05_Shapefiles\dataset_points_210402_08.shp   # Source Esri Shapefile(s)
- DestDataset_CSV2 = C:\Users\Sien Benoit\OneDrive - UGent\Werk_UGent\Doctoraat\Datasets_routes\DataFietsbarometerVL_210402\06_LinkingObjFactors\Points\Direction   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Points dataset of all users (!) that needs additional new attributes
Note: Liink the segment-id's of a student to the points of a student.
Note: Find the incoming segment (from_segm) and outgoing segment (to_segm) for each point
Note: Join the datasets so that every node gets the angle for the incoming segment (from_segm) and the outgoing segment (to_segm).
Note: Calculate the direction of the route of a student at a node by subtracting the angle of the incoming and outgoing segment. Negative values are taken the opposite and positive values are extracted from 360°.
dataset_points_210402_08 (reader SHAPEFILE_2)
    attributes: node_stud char(254), node_id long, student_id long, school_id long, municipal char(254), safe_sc long, transp_mod char(254), cyclist short, volu short, speed short, obst short, cond short, light short, space short, rules short, signs short, sight short, volu_sc long, speed_sc long, obst_sc long, cond_sc long, light_sc long, cutof_sc long, cross_sc long, acci_sc long, infra_sc long, time char(254), time_cat char(254), gender char(254), age long
    -> PointOnLineOverlayer [POINT]
    -> FeatureJoiner_start [RIGHT]
    -> FeatureJoiner_end [RIGHT]
Note: Segments of the routes of the adolescents with indication of the direction.
Note: Find segments of which the start node or the end node is in the points dataset
Note: Short segments cannot be cutof a distance of length - 10, so must be handled separately.
Note: Take the first 10 m of the segment if an assessed node is a start node, or the last 10 m of the segment if an assessed node is an end node. Take only the last meter if there is a short segment.
Note: Swicth the direction of the snipped segment so that the end node becomes the start node
Note: Calculate the horizontal angle of the snipped segments where the node from the points dataset is the start node of the segment. The angle is calculated from the east counterclockwise.
Note: Only keep the necessary attributes (node_id for matching, edge_id, angle) and join the datasets back together.
Note: Join the to- and from-datasets back together and aggregate the attributes, grouped by student id and node id so that every node of a student has an angle for the incoming segment and the outgoing segment.
Note: Select the necessary attributes and write to a csv file that can be joined to the original segments shapefile.
routesegments_2020_2021 (reader SHAPEFILE_1)
    attributes: student_id long, edge_id long, direction long, start_node long, end_node long
    -> PointOnLineOverlayer [LINE]
    -> FeatureJoiner_start [LEFT]
    -> FeatureJoiner_end [LEFT]

Bookmark: Find which points are on which segments
PointOnLineOverlayer
    DEAGGREGATE_INPUT = Yes
    LIST_NAME = segm_
    MEASURE_TYPE = Continuous
    MERGE_MEASURES = Yes
    OV_ATTR = _overlaps
    TOLERANCE = 0
    POINT -> ListExploder
ListExploder
    ATTR_ACCUM_MODE = Prefix List Attributes
    INCOMING_PREFIX = segm_
    INDEX_ATTR = _element_index
    LIST_ATTR = segm_{}
    ELEMENTS -> Tester
Tester
    BOOL_OP = OR
    COMPOSITE_TEST = 1
    TEST_CLAUSE = TEST @Value(student_id) = @Value(segm_student_id)
    TEST_MODE = TEST
    PASSED -> AttributeManager

Bookmark: Find the from_segm and to_segm
AttributeManager
    ATTR_TABLE:
      RENAME_SET_VALUE student_id
      SET_TO from_segment = FME_CONDITIONAL:DEFAULT_VALUE''not found''BOOL_OP;AND;COMPOSITE_TEST;1 AND 2 AND 3;TEST @Value(segm_direction) = 1;TEST @Value(segm_end_node) = @Value(node_id);TEST @Value(segm_student_id) = @Value(student_id)'@Value(segm_edge_id)'BOOL_OP;AND;COMPOSITE_TEST;1 AND 2 AND 3;TEST @Value(segm_direction) = 0;TEST @Value(segm_start_node) = @Value(node_id);TEST @Value(segm_student_id) = @Value(student_id)'@Value(segm_edge_id)'FME_NUM_CONDITIONS3___
      SET_TO to_segment = FME_CONDITIONAL:DEFAULT_VALUE''not found''BOOL_OP;AND;COMPOSITE_TEST;1 AND 2 AND 3;TEST @Value(segm_direction) = 0;TEST @Value(segm_end_node) = @Value(node_id);TEST @Value(segm_student_id) = @Value(student_id)'@Value(segm_edge_id)'BOOL_OP;AND;COMPOSITE_TEST;1 AND 2 AND 3;TEST @Value(segm_direction) = 1;TEST @Value(segm_start_node) = @Value(node_id);TEST @Value(segm_student_id) = @Value(student_id)'@Value(segm_edge_id)'FME_NUM_CONDITIONS3___
      REMOVE node_stud
      REMOVE school_id
      REMOVE municipal
      REMOVE safe_sc
      REMOVE transp_mod
      REMOVE cyclist
      REMOVE volu
      REMOVE speed
      REMOVE obst
      REMOVE cond
      REMOVE light
      REMOVE space
      REMOVE rules
      REMOVE signs
      REMOVE sight
      REMOVE volu_sc
      REMOVE speed_sc
      REMOVE obst_sc
      REMOVE cond_sc
      REMOVE light_sc
      REMOVE cutof_sc
      REMOVE cross_sc
      REMOVE acci_sc
      REMOVE infra_sc
      REMOVE time
      REMOVE time_cat
      REMOVE gender
      REMOVE age
    -> Aggregator
Aggregator
    ACCUM_ATTRS_NAME = Merge Incoming Attributes
    AGGREGATE_TYPE = Homogeneous Collection (If Possible)
    GROUP_BY = student_id node_id
    LIST_ATTRS_TO_INCLUDE = from_segment to_segment
    LIST_NAME = list_
    MODE = Geometry - Assemble One Level
    SEP = ,
    AGGREGATE -> AttributeManager_2
AttributeManager_2
    ATTR_TABLE:
      SET_TO to_segment_selection = FME_CONDITIONAL:DEFAULT_VALUE'_FME_NO_OP_'BOOL_OP;OR;COMPOSITE_TEST;1;TEST @Value(list_{0}.to_segment) != 'not found''@Value(list_{0}.to_segment)'BOOL_OP;OR;COMPOSITE_TEST;1;TEST @Value(list_{1}.to_segment) != 'not found''@Value(list_{1}.to_segment)'FME_NUM_CONDITIONS3___
      SET_TO from_segment_selection = FME_CONDITIONAL:DEFAULT_VALUE'_FME_NO_OP_'BOOL_OP;OR;COMPOSITE_TEST;1;TEST @Value(list_{0}.from_segment) != 'not found''@Value(list_{0}.from_segment)'BOOL_OP;OR;COMPOSITE_TEST;1;TEST @Value(list_{1}.from_segment) != 'not found''@Value(list_{1}.from_segment)'FME_NUM_CONDITIONS3___
    -> AttributeManager_3
AttributeManager_3
    ATTR_TABLE:
      REMOVE _overlaps
      REMOVE _element_index
      RENAME_SET_VALUE to_segment_selection > to_segm
      RENAME_SET_VALUE from_segment_selection > from_segm
      REMOVE from_segment
      REMOVE to_segment
      REMOVE segm_student_id
      REMOVE segm_edge_id
      REMOVE segm_direction
      REMOVE segm_start_node
      REMOVE segm_end_node
      REMOVE list_{}.from_segment
      REMOVE list_{}.to_segment
    -> FeatureJoiner_from [LEFT]
    -> FeatureJoiner_to [LEFT]

Bookmark: Orient the segments
FeatureJoiner_start
    ATTR_CONFLICT_RES = Use Left
    GEOMETRY_HANDLING = Use Left
    JOIN_KEYS = start_node node_id AUTO
    JOIN_MODE = Inner
    JOINED -> Snipper_start
FeatureJoiner_end
    ATTR_CONFLICT_RES = Use Left
    GEOMETRY_HANDLING = Use Left
    JOIN_KEYS = end_node node_id AUTO
    JOIN_MODE = Inner
    JOINED -> Tester_2

Bookmark: Snip 10 m of the segments
Snipper_start
    DEAGGREGATE_INPUT = YES
    ENDLOCATIONATTR = 10
    MEASUREMENTTYPE = 2D
    SNIPMODE = Distance (Value)
    STARTLOCATIONATTR = 0
    -> HorizontalAngleCalculator_2
Snipper_end
    DEAGGREGATE_INPUT = YES
    ENDLOCATIONATTR = @Length()
    MEASUREMENTTYPE = 2D
    SNIPMODE = Distance (Value)
    STARTLOCATIONATTR = @Length() - 10
    -> Orientor_2
Snipper_end_2
    DEAGGREGATE_INPUT = YES
    ENDLOCATIONATTR = @Length()
    MEASUREMENTTYPE = 2D
    SNIPMODE = Distance (Value)
    STARTLOCATIONATTR = @Length() - 1
    -> Orientor_2

Bookmark: Find the horizontal angle
HorizontalAngleCalculator_2
    ANGLE_TYPE = Feature
    UNIT_OUTPUT = DEG
    -> AttributeManager_4
HorizontalAngleCalculator
    ANGLE_TYPE = Feature
    UNIT_OUTPUT = DEG
    -> AttributeManager_5

Bookmark: Select attributes and join the datasets together.
AttributeManager_4
    ATTR_TABLE:
      REMOVE _azimuth
      REMOVE _X
      REMOVE _Y
      RENAME_SET_VALUE _angle > start_angle
      REMOVE student_id
      RENAME_SET_VALUE edge_id > start_edge_id
      REMOVE direction
      REMOVE start_node
      REMOVE end_node
      REMOVE _creation_instance
      REMOVE _x
      REMOVE _y
      REMOVE _z
      REMOVE _xEnd
      REMOVE _yEnd
      REMOVE _zEnd
      REMOVE node_stud
      RENAME_SET_VALUE node_id > node_id_match
      REMOVE school_id
      REMOVE municipal
      REMOVE safe_sc
      REMOVE transp_mod
      REMOVE cyclist
      REMOVE volu
      REMOVE speed
      REMOVE obst
      REMOVE cond
      REMOVE light
      REMOVE space
      REMOVE rules
      REMOVE signs
      REMOVE sight
      REMOVE volu_sc
      REMOVE speed_sc
      REMOVE obst_sc
      REMOVE cond_sc
      REMOVE light_sc
      REMOVE cutof_sc
      REMOVE cross_sc
      REMOVE acci_sc
      REMOVE infra_sc
      REMOVE time
      REMOVE time_cat
      REMOVE gender
      REMOVE age
    -> AttributeManager_7
AttributeManager_5
    ATTR_TABLE:
      REMOVE _azimuth
      REMOVE _X
      REMOVE _Y
      RENAME_SET_VALUE _angle > end_angle
      REMOVE student_id
      RENAME_SET_VALUE edge_id > end_edge_id
      REMOVE direction
      REMOVE start_node
      REMOVE end_node
      REMOVE _creation_instance
      REMOVE _x
      REMOVE _y
      REMOVE _z
      REMOVE _xEnd
      REMOVE _yEnd
      REMOVE _zEnd
      REMOVE node_stud
      RENAME_SET_VALUE node_id > node_id_match
      REMOVE school_id
      REMOVE municipal
      REMOVE safe_sc
      REMOVE transp_mod
      REMOVE cyclist
      REMOVE volu
      REMOVE speed
      REMOVE obst
      REMOVE cond
      REMOVE light
      REMOVE space
      REMOVE rules
      REMOVE signs
      REMOVE sight
      REMOVE volu_sc
      REMOVE speed_sc
      REMOVE obst_sc
      REMOVE cond_sc
      REMOVE light_sc
      REMOVE cutof_sc
      REMOVE cross_sc
      REMOVE acci_sc
      REMOVE infra_sc
      REMOVE time
      REMOVE time_cat
      REMOVE gender
      REMOVE age
    -> AttributeManager_7
AttributeManager_7
    ATTR_TABLE:
      RENAME_SET_VALUE start_angle > angle
      RENAME_SET_VALUE start_edge_id > edge_id
      RENAME_SET_VALUE end_angle > angle
      RENAME_SET_VALUE end_edge_id > edge_id
    -> FeatureJoiner_from [RIGHT]
    -> FeatureJoiner_to [RIGHT]

Bookmark: Separate long and short segments
Tester_2
    BOOL_OP = OR
    COMPOSITE_TEST = 1
    TEST_CLAUSE = TEST @Length() > 10
    TEST_MODE = TEST
    PASSED -> Snipper_end
    FAILED -> Snipper_end_2

Bookmark: Swicth direction
Orientor_2
    FLIP_APPEARANCES_CHOICE = Yes
    KIND = REVERSE
    ORIENTED -> HorizontalAngleCalculator

Bookmark: Find the angle for the from_segm and to_segm
FeatureJoiner_from
    ATTR_CONFLICT_RES = Use Left
    GEOMETRY_HANDLING = Use Left
    JOIN_KEYS = from_segm edge_id AUTO node_id node_id_match AUTO
    JOIN_MODE = Inner
    JOINED -> AttributeManager_from
AttributeManager_from
    ATTR_TABLE = RENAME_SET_VALUE angle > from_angle
    -> AttributeManager_10
FeatureJoiner_to
    ATTR_CONFLICT_RES = Use Left
    GEOMETRY_HANDLING = Use Left
    JOIN_KEYS = to_segm edge_id AUTO node_id node_id_match AUTO
    JOIN_MODE = Inner
    JOINED -> AttributeManager_to
AttributeManager_to
    ATTR_TABLE = RENAME_SET_VALUE angle > to_angle
    -> AttributeManager_10

Bookmark: Join the datasets back together and aggregate the from- and to-angle attributes
AttributeManager_10
    ATTR_TABLE = REMOVE edge_id
    -> Aggregator_2
Aggregator_2
    ACCUM_ATTRS_NAME = Merge Incoming Attributes
    AGGREGATE_TYPE = Homogeneous Collection (If Possible)
    GROUP_BY = student_id node_id
    MODE = Geometry - Assemble One Level
    SEP = ,
    AGGREGATE -> AttributeManager_12

Bookmark: Calculate the direction
AttributeManager_12
    ATTR_TABLE:
      SET_TO direction_temp = @Evaluate(@Value(from_angle)-@Value(to_angle))
      SET_TO direction = FME_CONDITIONAL:DEFAULT_VALUE'@Evaluate(360-@Value(direction_temp))'BOOL_OP;OR;COMPOSITE_TEST;1;TEST direction_temp ATTRIBUTE_VALUE_NULL _FME_BLANK_STRING_''BOOL_OP;OR;COMPOSITE_TEST;1;TEST @Value(direction_temp) < 0'@Evaluate(-@Value(direction_temp))'FME_NUM_CONDITIONS3___
    -> AttributeManager_6

Bookmark: Write to csv.
AttributeManager_6
    ATTR_TABLE:
      REMOVE to_segm
      REMOVE from_segm
      REMOVE from_angle
      REMOVE to_angle
      REMOVE direction_temp
      REMOVE node_id_match
    -> Direction (writer CSV2_1)
Direction (writer CSV2_1)
    attributes: student_id string, node_id string, direction string
