FME workspace NrRoads.fmw

Parameters:
- SourceDataset_SHAPEFILE = C:\Users\Sien Benoit\OneDrive - UGent\Werk_UGent\Doctoraat\Datasets_routes\DataFietsbarometerVL_210402\06_LinkingObjFactors\Points\dataset_points_210402_08.shp   # Source Esri Shapefile(s)
- SourceDataset_SHAPEFILE_3 = C:\Users\Sien Benoit\OneDrive - UGent\Werk_UGent\Doctoraat\Datasets_environment\nrroads\roads_vlaanderen_edges_2020_2021.shp   # Source Esri Shapefile(s)
- DestDataset_CSV2 = C:\Users\Sien Benoit\OneDrive - UGent\Werk_UGent\Doctoraat\Datasets_routes\DataFietsbarometerVL_210402\06_LinkingObjFactors\Points\NrRoads   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Points dataset that needs additional new attributes
Note: Create a buffer of 10 m around every assessed intersection.
Note: Find all lines that are in the buffer of a node and count them.
Note: Write to a csv file that can be joined to the original pionts shapefile.
dataset_points_210402_08 (reader SHAPEFILE_1)
    attributes: node_id long
    -> Bufferer
Note: Road segments used in the Bike Barometer (2020-2021)
roads_vlaanderen_edges_2020_2021 (reader SHAPEFILE_2)
    attributes: gid long, osm_id char(10), name char(100), eenrichtin char(1), edge_id long, startpoint char(254), endpoint char(254), start_node long, end_node long
    -> LineOnAreaOverlayer [LINE]

Bookmark: Buffer the intersections
Bufferer
    ANGLE = 22.5
    CAP_STYLE = Round
    CORNER_STYLE = Round
    MODE = AREA
    OFFSET = 10
    OFFSET_UNITS = NONE
    BUFFERED -> LineOnAreaOverlayer [AREA]

Bookmark: Find lines in the buffers
LineOnAreaOverlayer
    CLEANING_TOLERANCE = Automatic
    DEAGGREGATE_INPUT = Yes
    OV_ATTR = NrRoads
    AREA -> NrRoads (writer CSV2_1)

Bookmark: Write to csv
NrRoads (writer CSV2_1)
    attributes: node_id string, NrRoads string
