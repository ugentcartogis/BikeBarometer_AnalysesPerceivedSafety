FME workspace Rails.fmw

Parameters:
- SourceDataset_SHAPEFILE = C:\Users\Sien Benoit\OneDrive - UGent\Werk_UGent\Doctoraat\Datasets_routes\DataFietsbarometerVL_210402\06_LinkingObjFactors\Points\dataset_points_210402_08.shp   # Source Esri Shapefile(s)
- SourceDataset_SHAPEFILE_3 = C:\Users\Sien Benoit\OneDrive - UGent\Werk_UGent\Doctoraat\Datasets_environment\rails\GRB\Rails_projected.shp   # Source Esri Shapefile(s)
- SourceDataset_GEOTIFF = C:\Users\Sien Benoit\OneDrive - UGent\Werk_UGent\Doctoraat\Datasets_environment\height\DTM_Flanders\DTM_Flanders.tif   # Source GeoTIFF File(s)
- DestDataset_CSV2 = C:\Users\Sien Benoit\OneDrive - UGent\Werk_UGent\Doctoraat\Datasets_routes\DataFietsbarometerVL_210402\06_LinkingObjFactors\Points\Rails   # Destination CSV (Comma Separated Value) Folder

Readers:
- SHAPEFILE_1: SHAPEFILE from $(SourceDataset_SHAPEFILE)
- SHAPEFILE_2: SHAPEFILE from $(SourceDataset_SHAPEFILE_3)
- GEOTIFF_1: GEOTIFF from $(SourceDataset_GEOTIFF)

Writers:
- CSV2_1: CSV2 to $(DestDataset_CSV2)

Note: Train and tram rails in Flanders (also unused rails) mapped in the GRB as wrl
Note: Remove unnecessary attributes
Note: Extract the rails that lie in a buffer of an intersection.
Note: Extract the midpoint of the intersected rail
Note: Calculate the height of the intersections and of the midpoints of the intersected rails. Remove unnecessary attributes.
Note: Match the midpoints with the original nodes. If the difference in height is more than 2 m, there is no real intersection (but possibly a bridge or tunnel). Else, the intersection is real.
Note: Join the points to the original points. Points that did not have an intersection get a 'false' value for the attribute 'rails'.
Note: Sort the records per node and remove duplicates so that a point is assigned a true value when at least one of its intersected rails has real intersection.
Note: Write to a csv file that can be joined to the original points shapefile.
Rails_projected (reader SHAPEFILE_2)
    attributes: OIDN number(15,0), UIDN number(15,0), VERSIE short, BEGINDATUM date, VERSDATUM date, BHRDR short, LBLBHRDR char(32), LIJNNR char(10), OPNDATUM date, BGNINV short, LBLBGNINV char(32), LENGTE double
    -> AttributeManager
Note: Points dataset that needs additional new attributes
Note: Create a buffer of 10 m around every assessed intersection.
dataset_points_210402_08 (reader SHAPEFILE_1)
    attributes: node_id long
    -> Bufferer
    -> PointOnRasterValueExtractor_2 [POINT]
    -> FeatureJoiner_3 [LEFT]
Note: Digital Terrain Model of (part of) Flanders
GEOTIFF (reader GEOTIFF_1)
    -> PointOnRasterValueExtractor [RASTER]
    -> PointOnRasterValueExtractor_2 [RASTER]

Bookmark: Keep only the OID
AttributeManager
    ATTR_TABLE:
      REMOVE UIDN
      REMOVE VERSIE
      REMOVE BEGINDATUM
      REMOVE VERSDATUM
      REMOVE BHRDR
      REMOVE LBLBHRDR
      REMOVE LIJNNR
      REMOVE OPNDATUM
      REMOVE BGNINV
      REMOVE LBLBGNINV
      REMOVE LENGTE
    -> LineOnAreaOverlayer [LINE]

Bookmark: Buffer the intersections
Bufferer
    ANGLE = 22.5
    CAP_STYLE = Round
    CORNER_STYLE = Round
    MODE = AREA
    OFFSET = 10
    OFFSET_UNITS = NONE
    BUFFERED -> LineOnAreaOverlayer [AREA]

Bookmark: Find rails in buffer
LineOnAreaOverlayer
    ATTR_ACCUM_MODE = Merge Incoming
    ATTR_CONFLICT_RES = Use Original
    CLEANING_TOLERANCE = Automatic
    DEAGGREGATE_INPUT = Yes
    OV_ATTR = _overlaps
    LINE -> Tester
Tester
    BOOL_OP = OR
    COMPOSITE_TEST = 1
    TEST_CLAUSE = TEST @Value(_overlaps) > 0
    TEST_MODE = TEST
    PASSED -> Snipper

Bookmark: Find the midpoint
Snipper
    DEAGGREGATE_INPUT = YES
    ENDLOCATIONATTR = 50
    MEASUREMENTTYPE = 2D
    SNIPMODE = Distance (Percentage)
    STARTLOCATIONATTR = 50
    -> PointOnRasterValueExtractor [POINT]

Bookmark: Find the height
PointOnRasterValueExtractor
    INTERPOLATION_TYPE_NAME = Nearest Neighbor
    POINT -> AttributeManager_3
AttributeManager_3
    ATTR_TABLE:
      REMOVE fme_basename
      RENAME_SET_VALUE _band{}.value > _band_r{}.value
      REMOVE _band{}.palette{}.value
    -> FeatureJoiner [RIGHT]
PointOnRasterValueExtractor_2
    INTERPOLATION_TYPE_NAME = Nearest Neighbor
    POINT -> AttributeManager_2
AttributeManager_2
    ATTR_TABLE:
      REMOVE fme_basename
      RENAME_SET_VALUE _band{}.value > _band_p{}.value
      REMOVE _band{}.palette{}.value
    -> FeatureJoiner [LEFT]

Bookmark: Find the real intersections
FeatureJoiner
    ATTR_CONFLICT_RES = Use Left
    GEOMETRY_HANDLING = Use Left
    JOIN_KEYS = node_id node_id AUTO
    JOIN_MODE = Inner
    JOINED -> AttributeCreator
AttributeCreator
    ATTR_TABLE = SET_TO rails = FME_CONDITIONAL:DEFAULT_VALUE'true'BOOL_OP;OR;COMPOSITE_TEST;1;NUM_TEST @abs(@Value(_band_r{0}.value)-@Value(_band_p{0}.value)) > 2'false'FME_NUM_CONDITIONS2___
    -> FeatureJoiner_3 [RIGHT]

Bookmark: Join the intersected points with the original points
FeatureJoiner_3
    ATTR_CONFLICT_RES = Use Left
    GEOMETRY_HANDLING = Use Left
    JOIN_KEYS = node_id node_id AUTO
    JOIN_MODE = Left
    JOINED -> AttributeManager_4
AttributeManager_4
    ATTR_TABLE:
      SET_TO rails = FME_CONDITIONAL:DEFAULT_VALUE'_FME_NO_OP_'BOOL_OP;OR;COMPOSITE_TEST;1;TEST rails ATTRIBUTE_VALUE_NULL _FME_BLANK_STRING_'false'FME_NUM_CONDITIONS2___
      REMOVE OIDN
      REMOVE _band_p{}.value
      REMOVE _overlaps
      REMOVE _band_r{}.value
    -> Sorter

Bookmark: Remove duplicates
Sorter
    SORT_PARM = node_id ALPHA ASCENDING rails ALPHA DESCENDING
    SORTED -> DuplicateFilter
DuplicateFilter
    INPUT_ORDERED_CHOICE = No
    KEYATTR = node_id
    UNIQUE -> Rails (writer CSV2_1)

Bookmark: Write to csv
Rails (writer CSV2_1)
    attributes: rails string, node_id string
