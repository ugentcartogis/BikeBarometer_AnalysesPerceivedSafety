FME workspace MaxSpeed.fmw

Parameters:
- SourceDataset_SHAPEFILE_3 = C:\Users\Sien Benoit\OneDrive - UGent\Werk_UGent\Doctoraat\Datasets_routes\DataFietsbarometerVL_210402\06_LinkingObjFactors\Points\dataset_points_210402_08.shp   # Source Esri Shapefile(s)
- SourceDataset_SHAPEFILE = C:\Users\Sien Benoit\OneDrive - UGent\Werk_UGent\Doctoraat\Datasets_environment\maxspeed\MOW\Snelheid_wegen_Vlaanderen_projected.shp   # Source Esri Shapefile(s)
- DestDataset_CSV2 = C:\Users\Sien Benoit\OneDrive - UGent\Werk_UGent\Doctoraat\Datasets_routes\DataFietsbarometerVL_210402\06_LinkingObjFactors\Points\MaxSpeed   # Destination CSV (Comma Separated Value) Folder

Readers:
- SHAPEFILE_2: SHAPEFILE from $(SourceDataset_SHAPEFILE_3)
- SHAPEFILE_1: SHAPEFILE from $(SourceDataset_SHAPEFILE)

Writers:
- CSV2_1: CSV2 to $(DestDataset_CSV2)

Note: Segments of the MOW dataset projected to Lambert72
Note: Find all lines that are in the buffer of a node.
Note: Calculate the average max speed along the lines in the buffer.
Note: Write to a csv file that can be joined to the original points shapefile.
Snelheid_wegen_Vlaanderen_projected (reader SHAPEFILE_1)
    attributes: FID_1 long, WEGSEGMENT long, SNELHEID short, IDENT8 char(8), Shape__Len double
    -> LineOnAreaOverlayer [LINE]
Note: Points dataset that needs additional new attributes
Note: Create a buffer of 10 m around every assessed intersection.
dataset_points_210402_08 (reader SHAPEFILE_2)
    attributes: node_id long
    -> Bufferer

Bookmark: Buffer the intersections
Bufferer
    ANGLE = 22.5
    CAP_STYLE = Round
    CORNER_STYLE = Round
    MODE = AREA
    OFFSET = 10
    OFFSET_UNITS = NONE
    BUFFERED -> LineOnAreaOverlayer [AREA]

Bookmark: Find lines in the buffers
LineOnAreaOverlayer
    CANDIDATE_LIST_ATTRS_TO_INCLUDE = SNELHEID
    CANDIDATE_LIST_ATTRS_TO_INCLUDE_MODE = Selected Attributes
    CANDIDATE_LIST_NAME = mow_
    CLEANING_TOLERANCE = Automatic
    DEAGGREGATE_INPUT = Yes
    OV_ATTR = _overlaps
    AREA -> ListStatisticsCalculator

Bookmark: Calculate the average max speed at the intersection
ListStatisticsCalculator
    LIST_ATTR = mow_{}.SNELHEID
    PREFIX = stats_
    -> AttributeManager
AttributeManager
    ATTR_TABLE:
      REMOVE _overlaps
      REMOVE stats_min
      REMOVE stats_max
      REMOVE stats_median
      REMOVE stats_count
      REMOVE stats_sum
      REMOVE stats_range
      RENAME_SET_VALUE stats_mean > MaxSpeed
      REMOVE stats_stdev
      REMOVE stats_stdevp
      REMOVE stats_mode
      REMOVE mow_{}.SNELHEID
    -> MaxSpeed (writer CSV2_1)

Bookmark: Write to csv
MaxSpeed (writer CSV2_1)
    attributes: node_id string, MaxSpeed string

FME custom transformer ListStatisticsCalculator
Calculates fundamental statistics of element values in the specified list, and adds attributes storing the calculation results to the feature.
    Only decimal numbers can be accepted as the list elements. 0 at the head of an element will be ignored. 
    If the incoming feature does not have list attribute with the specified name, or the list contains one or more non-numeric elements, then the feature will be output from the 
    <Rejected>
    port.
    Every rejected feature will have an attribute named "_liststats_error", which contains a text describing the rejected reason. 
    This transformer contains a Python script, which was tested with both Python 2.7 interpreter and 3.6 interpreter.
Parameters
    List Attribute
    :
    Specify a list name which contains numeric elements.
    Prefix of Statistics Attributes
    :
    Specify a common prefix which should be added to names of result attributes. This can be set to empty string, if unnecessary.
    Output features will have these attributes if you specify "stats_" to this parameter.
    -----
    stats_min - The minimum value in all the values. 
    stats_max - The maximum value in all the values. 
    stats_median - The middle value of all the values. 
    stats_count - The number of the elements. 
    stats_sum - The sum of all the values. 
    stats_range - The difference between the minimum and the maximum. i.e. equals to the maximum minus the minimum. 
    stats_mean - The average of all the values. 
    stats_stdev - The standard deviation (sample) of all the values. This will be empty if the number of elements is equal to 1.
    stats_stdevp - The standard deviation (population) of all the values. 
    stats_mode - The most frequent of all the values. If two or more values occur with the highest frequency, one of them will be returned randomly. 
    -----

Parameters:
- LIST_ATTR =   # " " List Attribute
- PREFIX = stats_   # TYPE:varchar(200) Prefix of Statistics Attributes

Input (input)
    -> ParameterFetcher
ParameterFetcher
    ATTR_LIST = liststatisticscalculator.list_attr {$(LIST_ATTR)}
    -> PythonCaller
PythonCaller
    NEW_ATTRIBUTES = min.liststatisticscalculator max.liststatisticscalculator median.liststatisticscalculator count.liststatisticscalculator sum.liststatisticscalculator range.liststatisticscalculator mean.liststatisticscalculator stdev.liststatisticscalculator stdevp.liststatisticscalculator mode.liststatisticscalculator liststatisticscalculator.histogram{}.count liststatisticscalculator.histogram{}.value liststatisticscalculator.flag
    PYTHONSOURCE:
      # 2018-06-14, Takashi Iijime, Updated to support Python 3.x interpreter.
      # 2016-06-24, Takashi Iijima, Added stdevp - standard deviation (population).
      # 2014-08-02, Takashi Iijima, Original Implementation

      import fmeobjects, locale, re, math

      class ListStatisticsCalculator(object):
          def __init__(self):
              import platform
              if platform.python_version_tuple()[0] == '2':
                  loc = locale.getdefaultlocale()
                  enc = loc[1] if loc else 'utf_8'
                  self.toStr = lambda s: s.encode(enc) if isinstance(s, unicode) else s
              else:
                  self.toStr = lambda s: s

          def input(self, feature):
              try:
                  listName = self.toStr(feature.getAttribute('liststatisticscalculator.list_attr'))
                  m = re.match(r'^(.+)\{\}(.*)$', listName)

                  front, index, back = m.group(1), 0, m.group(2)
                  values, total, histogram = [], 0.0, {}
                  while True:
                      v = feature.getAttribute('%s{%d}%s' % (front, index, back))
                      if v == None:
                          break
                      v = float(v)
                      values.append(v)
                      total += v
                      histogram[v] = histogram.setdefault(v, 0) + 1
                      index += 1

                  # Number of elements.
                  count = len(values)
                  if count < 1:
                      raise Exception('could not find valid element')
                  values.sort() # ascending sort

                  # Calculate median, average (mean) and standard deviation.
                  mid = count // 2
                  median = values[mid] if count % 2 else 0.5 * (values[mid - 1] + values[mid])
                  avrg = total / count
                  s = sum([(v - avrg)**2 for v in values])
                  stdev = math.sqrt(s / (count - 1)) if 1 < count else ''
                  stdevp = math.sqrt(s / count)

                  # Find mode.
                  mode, num = None, 0
                  for i, v in enumerate(sorted(histogram.keys())):
                      n = histogram[v]
                      if num < n:
                          mode, num = v, n
                      # Reserved: Set histogram elements
                      #feature.setAttribute('liststatisticscalculator.histogram{%d}.count' % i, n)
                      #feature.setAttribute('liststatisticscalculator.histogram{%d}.value' % i, v)

                  # Set statistics attributes.
                  feature.setAttribute('min.liststatisticscalculator', values[0])
                  feature.setAttribute('max.liststatisticscalculator', values[-1])
                  feature.setAttribute('median.liststatisticscalculator', median)
                  feature.setAttribute('count.liststatisticscalculator', count)
                  feature.setAttribute('sum.liststatisticscalculator', total)
                  feature.setAttribute('range.liststatisticscalculator', values[-1] - values[0])
                  feature.setAttribute('mean.liststatisticscalculator', avrg)
                  feature.setAttribute('stdev.liststatisticscalculator', stdev)
                  feature.setAttribute('stdevp.liststatisticscalculator', stdevp)
                  feature.setAttribute('mode.liststatisticscalculator', mode)

                  # Set flag.
                  feature.setAttribute('liststatisticscalculator.flag', 1)

              except Exception as ex:
                  feature.setAttribute('_liststats_error', '%s' % ex)
                  feature.setAttribute('liststatisticscalculator.flag', 0)

              self.pyoutput(feature)
    PYTHONSYMBOL = ListStatisticsCalculator
    -> Tester
Tester
    BOOL_OP = OR
    TEST_CLAUSE = TEST @Value(liststatisticscalculator.flag) = 1
    TEST_MODE = Automatic
    PASSED -> BulkAttributeRenamer
    FAILED -> BulkAttributeRemover_2
Note: Add common prefix
BulkAttributeRenamer
    ATTRCHOICE = Selected Attributes
    ATTRLIST = min.liststatisticscalculator max.liststatisticscalculator median.liststatisticscalculator count.liststatisticscalculator sum.liststatisticscalculator range.liststatisticscalculator mean.liststatisticscalculator stdev.liststatisticscalculator stdevp.liststatisticscalculator mode.liststatisticscalculator
    PATTERN_ACTION_DISP = Add String Prefix
    REPLACE_STR = $(PREFIX)
    -> BulkAttributeRenamer_2
Note: Remove extra suffix
BulkAttributeRenamer_2
    ATTRCHOICE = All Attributes
    CASE_DISP = yes
    PATTERN_ACTION_DISP = Remove Suffix String
    REPLACE_STR = .liststatisticscalculator
    -> BulkAttributeRemover
Note: Remove unnecessary attributes
BulkAttributeRemover
    ATTR_EXP = ^liststatisticscalculator
    -> Output (output)
Output (output)
BulkAttributeRemover_2
    ATTR_EXP = liststatisticscalculator
    -> AttributeExposer
Note: AttributeExposer [AttributeExposer] / Attributes To Expose: _liststats_error
AttributeExposer
    ATTR_LIST = _liststats_error
    -> <Rejected> (output)
<Rejected> (output)
