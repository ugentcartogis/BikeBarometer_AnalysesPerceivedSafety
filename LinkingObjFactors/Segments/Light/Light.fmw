FME workspace Light.fmw

Parameters:
- SourceDataset_SHAPEFILE = $(FME_MF_DIR)Lighting_projected.shp   # Source Esri Shapefile(s)
- SourceDataset_SHAPEFILE_3 = C:\Users\Sien Benoit\OneDrive - UGent\Werk_UGent\Doctoraat\Datasets_routes\DataFietsbarometerVL_210402\06_LinkingObjFactors\Segments\dataset_segments_210402_08_infra.shp   # Source Esri Shapefile(s)
- DestDataset_CSV2 = C:\Users\Sien Benoit\OneDrive - UGent\Werk_UGent\Doctoraat\Datasets_routes\DataFietsbarometerVL_210402\06_LinkingObjFactors\Segments\Light   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Light poles along roads in Flanders projected to Lambert72
Note: Calcutle the length in m of each segment
Note: Create a buffer of 15 m around each segment with no buffered area at the ends of the segment.
Note: Count the number of lights in each buffer
Note: The attribute 'light' gives the number of lights per 100 m for each segment.
Note: Select and rename the attributes and write to a csv file that can be joined to the original segments shapefile.
Lighting_projected (reader SHAPEFILE_1)
    attributes: OIDN number(15,0), UIDN number(15,0), VERSIE short, BEGINDATUM date, VERSDATUM date, TYPE short, LBLTYPE char(64), OPNDATUM date, BGNINV short, LBLBGNINV char(32)
    -> PointOnAreaOverlayer [POINT]
Note: Segments dataset that needs additional new attributes
dataset_segments_210402_08_infra (reader SHAPEFILE_2)
    attributes: segment_id long, mode char(254)
    -> LengthCalculator

Bookmark: Calculate length
LengthCalculator
    DIM = 2
    LEN_ATTR = _length
    MULT = 1
    -> Bufferer

Bookmark: Buffer each segment
Bufferer
    ANGLE = 22.5
    CAP_STYLE = None
    CORNER_STYLE = Bevel
    MODE = AREA
    OFFSET = 15
    OFFSET_UNITS = NONE
    BUFFERED -> PointOnAreaOverlayer [AREA]

Bookmark: Count lights
PointOnAreaOverlayer
    DEAGGREGATE_INPUT = Yes
    OV_ATTR = _lights
    POLYS_FIRST = NO
    AREA -> AttributeCreator

Bookmark: Convert the attributes
AttributeCreator
    ATTR_TABLE = SET_TO _lights_per_100m = @mult(@div(@Value(_lights),@Value(_length)),100)
    -> AttributeManager

Bookmark: Write to csv
AttributeManager
    ATTR_TABLE:
      REMOVE mode
      REMOVE _lights
      REMOVE _length
      RENAME_SET_VALUE _lights_per_100m > light
    -> Light (writer CSV2_1)
Light (writer CSV2_1)
    attributes: segment_id string, light real64
