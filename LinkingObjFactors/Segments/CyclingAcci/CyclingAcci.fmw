FME workspace CyclingAcci.fmw

Parameters:
- SourceDataset_SHAPEFILE_3 = C:\Users\Sien Benoit\OneDrive - UGent\Werk_UGent\Doctoraat\Datasets_routes\DataFietsbarometerVL_210402\06_LinkingObjFactors\Segments\dataset_segments_210402_08_infra.shp   # Source Esri Shapefile(s)
- SourceDataset_SHAPEFILE = C:\Users\Sien Benoit\OneDrive - UGent\Werk_UGent\Doctoraat\Datasets_environment\cyclingaccidents\MOW\CyclingAccidents_2017-2019_projected.shp   # Source Esri Shapefile(s)
- DestDataset_CSV2 = C:\Users\Sien Benoit\OneDrive - UGent\Werk_UGent\Doctoraat\Datasets_routes\DataFietsbarometerVL_210402\06_LinkingObjFactors\Segments\CyclingAcci   # Destination CSV (Comma Separated Value) Folder

Readers:
- SHAPEFILE_1: SHAPEFILE from $(SourceDataset_SHAPEFILE_3)
- SHAPEFILE_2: SHAPEFILE from $(SourceDataset_SHAPEFILE)

Writers:
- CSV2_1: CSV2 to $(DestDataset_CSV2)

Note: Cycling accidents that occurred in the period 2017 - 2019 in Flanders
Note: Calcutle the length in m of each segment
Note: Create a buffer of 10 m around each segment with no buffered area at the ends of the segment.
Note: Count the number of accidents in each buffer
Note: The attribute 'cyclingacci' gives the number of accidents per 100 m for each segment.
Note: Select and rename the attributes and write to a csv file that can be joined to the original segments shapefile.
CyclingAccidents_2017-2019_projected (reader SHAPEFILE_2)
    attributes: gemeente char(254), totaalBetr long, totaalZwaa long, totaalLich long, aantalDode long, locatie_1 char(254), kmp_1 double, locatie_2 char(254), kmp_2 double
    -> PointOnAreaOverlayer [POINT]
Note: Segments dataset that needs additional new attributes
dataset_segments_210402_08_infra (reader SHAPEFILE_1)
    attributes: segment_id long, mode char(254)
    -> LengthCalculator

Bookmark: Calculate length
LengthCalculator
    DIM = 2
    LEN_ATTR = _length
    MULT = 1
    -> Bufferer

Bookmark: Buffer each segment
Bufferer
    ANGLE = 22.5
    CAP_STYLE = None
    CORNER_STYLE = Bevel
    MODE = AREA
    OFFSET = 10
    OFFSET_UNITS = NONE
    BUFFERED -> PointOnAreaOverlayer [AREA]

Bookmark: Count accidents
PointOnAreaOverlayer
    DEAGGREGATE_INPUT = Yes
    OV_ATTR = _accidents
    POLYS_FIRST = NO
    AREA -> AttributeCreator

Bookmark: Convert the attributes
AttributeCreator
    ATTR_TABLE = SET_TO _acci_per_100m = @mult(@div(@Value(_accidents),@Value(_length)),100)
    -> AttributeManager

Bookmark: Write to csv
AttributeManager
    ATTR_TABLE:
      REMOVE mode
      REMOVE _length
      RENAME_SET_VALUE _acci_per_100m > cyclingacci
      REMOVE _accidents
    -> CyclingAcci (writer CSV2_1)
CyclingAcci (writer CSV2_1)
    attributes: segment_id string, cyclingacci string
