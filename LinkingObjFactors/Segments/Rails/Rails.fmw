FME workspace Rails.fmw

Parameters:
- SourceDataset_SHAPEFILE = $(FME_MF_DIR)Rails_projected.shp   # Source Esri Shapefile(s)
- SourceDataset_SHAPEFILE_3 = C:\Users\Sien Benoit\OneDrive - UGent\Werk_UGent\Doctoraat\Datasets_routes\DataFietsbarometerVL_210402\06_LinkingObjFactors\Segments\dataset_segments_210402_08_infra.shp   # Source Esri Shapefile(s)
- SourceDataset_GEOTIFF = C:\Users\Sien Benoit\OneDrive - UGent\Werk_UGent\Doctoraat\Datasets_routes\DataFietsbarometerVL_210402\06_LinkingObjFactors\Segments\DTM_Flanders\DTM_Flanders.tif   # Source GeoTIFF File(s)
- DestDataset_CSV2 = C:\Users\Sien Benoit\OneDrive - UGent\Werk_UGent\Doctoraat\Datasets_routes\DataFietsbarometerVL_210402\06_LinkingObjFactors\Segments\Rails   # Destination CSV (Comma Separated Value) Folder

Readers:
- SHAPEFILE_1: SHAPEFILE from $(SourceDataset_SHAPEFILE)
- SHAPEFILE_2: SHAPEFILE from $(SourceDataset_SHAPEFILE_3)
- GEOTIFF_1: GEOTIFF from $(SourceDataset_GEOTIFF)

Writers:
- CSV2_1: CSV2 to $(DestDataset_CSV2)

Note: Train and tram rails in Flanders (also unused rails) mapped in the GRB as wrl
Note: Remove unnecessary attributes
Note: Intersect the rails and the segments and ignore intersections between features in the same feature class. / Extract the lines of the rails that are intersected
Note: Keep only the first 10 m of the intersected rail
Note: First, add a point at 75 m to the north of the intersection point to create a line. Second, rotate this line based on the horizontal angle of the intersected rail. Finally, extract the end point of this rotated line.
Note: Calculate the height of the intersected points and the points at 75 m. Remove unnecessary attributes.
Note: Match points that belong together. If the difference in height is more than 2 m, there is no real intersection (but possibly a bridge or tunnel). Else, the intersection is real.
Note: Join the points to the original segments. Segments that did not have an intersection get a 'false' value for the attribut 'rails'.
Note: Sort the records per segment and remove duplicates so that a segment is assigned a true value when at least one of its subsegments has an intersection with a rail.
Note: Write to a csv file that can be joined to the original segments shapefile.
Rails_projected (reader SHAPEFILE_1)
    attributes: OIDN number(15,0), UIDN number(15,0), VERSIE short, BEGINDATUM date, VERSDATUM date, BHRDR short, LBLBHRDR char(32), LIJNNR char(10), OPNDATUM date, BGNINV short, LBLBGNINV char(32), LENGTE double
    -> AttributeManager
Note: Segments dataset that needs additional new attributes
dataset_segments_210402_08_infra (reader SHAPEFILE_2)
    attributes: segment_id long, mode char(254)
    -> Intersector
    -> FeatureJoiner_3 [LEFT]
Note: Digital Terrain Model of (part of) Flanders
GEOTIFF (reader GEOTIFF_1)
    -> PointOnRasterValueExtractor [RASTER]
    -> PointOnRasterValueExtractor_2 [RASTER]

Bookmark: Keep only the OID
AttributeManager
    ATTR_TABLE:
      REMOVE UIDN
      REMOVE VERSIE
      REMOVE BEGINDATUM
      REMOVE VERSDATUM
      REMOVE BHRDR
      REMOVE LBLBHRDR
      REMOVE LIJNNR
      REMOVE OPNDATUM
      REMOVE BGNINV
      REMOVE LBLBGNINV
      REMOVE LENGTE
    -> Intersector

Bookmark: Intersect
Intersector
    ATTRS_ACCUM_MODE = Merge Attributes
    CLEANING_TOLERANCE = Automatic
    DEAGGREGATE_INPUT = Yes
    DUPLICATE_Z_NODES = No
    GENERATE_LIST_DROP = NO
    MEASURE_TYPE = Continuous
    NODE_NUM_ATTR = _node_number
    OV_ATTR = _overlaps
    PERFORM_SELF_INTERSECTION = Yes
    SEG_ATTR = _segments
    SEPARATE_COLLINEAR_SEGMENTS = Yes
    INTERSECTED -> Tester_2
    NODE -> Tester
Tester_2
    BOOL_OP = AND
    COMPOSITE_TEST = 1 AND 2
    TEST_CLAUSE:
      TEST @Value(_segments) > 1
      TEST OIDN ATTRIBUTE_HAS_A_VALUE ""
    TEST_MODE = TEST
    PASSED -> PointOnLineOverlayer [LINE]
Tester
    BOOL_OP = AND
    COMPOSITE_TEST = 1 AND 2
    TEST_CLAUSE:
      TEST segment_id ATTRIBUTE_HAS_A_VALUE ""
      TEST OIDN ATTRIBUTE_HAS_A_VALUE ""
    TEST_MODE = TEST
    PASSED -> PointOnRasterValueExtractor [POINT]
    PASSED -> CoordinateExtractor
    PASSED -> PointOnLineOverlayer [POINT]
PointOnLineOverlayer
    ATTR_ACCUM_MODE = Prefix Incoming
    DEAGGREGATE_INPUT = Yes
    INCOMING_PREFIX = pre
    MEASURE_TYPE = Continuous
    MERGE_MEASURES = Yes
    OV_ATTR = _overlaps
    TOLERANCE = 0.1
    LINE -> Tester_3
Tester_3
    BOOL_OP = OR
    COMPOSITE_TEST = 1
    TEST_CLAUSE = TEST pre_node_number ATTRIBUTE_HAS_A_VALUE ""
    TEST_MODE = TEST
    PASSED -> Snipper

Bookmark: Snip the intersected rail lines
Snipper
    DEAGGREGATE_INPUT = YES
    ENDLOCATIONATTR = 10
    MEASUREMENTTYPE = 2D
    SNIPMODE = Distance (Value)
    STARTLOCATIONATTR = 0
    -> HorizontalAngleCalculator

Bookmark: Create a point at 75 m perpendicular to the snipped intersected rail
HorizontalAngleCalculator
    ANGLE_TYPE = Feature
    UNIT_OUTPUT = DEG
    -> DuplicateFilter
DuplicateFilter
    INPUT_ORDERED_CHOICE = No
    KEYATTR = pre_node_number
    UNIQUE -> FeatureJoiner_2 [RIGHT]
CoordinateExtractor
    IND = 0
    MODE = Specify Coordinate
    X_ATTR = _xco
    Y_ATTR = _yco
    Z_ATTR = _zco
    -> VertexCreator
VertexCreator
    MEASURE_TYPE = Continuous
    MISSING_VAL_MODE = Compute
    MODE_NAME = Add Point
    XVAL = @Value(_xco)
    YVAL = @Value(_yco) + 75
    -> FeatureJoiner_2 [LEFT]
FeatureJoiner_2
    ATTR_CONFLICT_RES = Use Left
    GEOMETRY_HANDLING = Use Left
    JOIN_KEYS = _node_number pre_node_number AUTO
    JOIN_MODE = Left
    JOINED -> Rotator
Rotator
    ANGLE = @Value(_angle)
    XORIG = @Value(_xco)
    YORIG = @Value(_yco)
    ROTATED -> CoordinateExtractor_2
CoordinateExtractor_2
    IND = -1
    MODE = Specify Coordinate
    X_ATTR = _xend
    Y_ATTR = _yend
    Z_ATTR = _zend
    -> VertexCreator_2
VertexCreator_2
    MEASURE_TYPE = Continuous
    MODE_NAME = Replace with Point
    XVAL = @Value(_xend)
    YVAL = @Value(_yend)
    -> PointOnRasterValueExtractor_2 [POINT]

Bookmark: Find the height
PointOnRasterValueExtractor_2
    INTERPOLATION_TYPE_NAME = Nearest Neighbor
    POINT -> AttributeManager_2
AttributeManager_2
    ATTR_TABLE:
      REMOVE fme_basename
      REMOVE mode
      REMOVE _xco
      REMOVE _yco
      REMOVE _zco
      REMOVE _azimuth
      REMOVE _X
      REMOVE _Y
      REMOVE _angle
      REMOVE preOIDN
      REMOVE presegment_id
      REMOVE premode
      REMOVE _overlaps
      REMOVE _segments
      REMOVE _creation_instance
      REMOVE _x
      REMOVE _y
      REMOVE _z
      REMOVE _xEnd
      REMOVE _yEnd
      REMOVE _zEnd
      REMOVE _xend
      REMOVE _yend
      REMOVE _zend
      RENAME_SET_VALUE _band{}.value > _band_a{}.value
      REMOVE _band{}.palette{}.value
    -> FeatureJoiner [RIGHT]
PointOnRasterValueExtractor
    INTERPOLATION_TYPE_NAME = Nearest Neighbor
    POINT -> AttributeManager_3
AttributeManager_3
    ATTR_TABLE:
      REMOVE fme_basename
      REMOVE OIDN
      REMOVE mode
      RENAME_SET_VALUE _band{}.value > _band_b{}.value
      REMOVE _band{}.palette{}.value
    -> FeatureJoiner [LEFT]

Bookmark: Find points where rails intersect
FeatureJoiner
    ATTR_CONFLICT_RES = Use Left
    GEOMETRY_HANDLING = Use Left
    JOIN_KEYS = _node_number _node_number AUTO
    JOIN_MODE = Inner
    JOINED -> AttributeCreator
AttributeCreator
    ATTR_TABLE = SET_TO rails = FME_CONDITIONAL:DEFAULT_VALUE'true'BOOL_OP;OR;COMPOSITE_TEST;1;NUM_TEST @abs(@Value(_band_a{0}.value)-@Value(_band_b{0}.value)) > 2'false'FME_NUM_CONDITIONS2___
    -> FeatureJoiner_3 [RIGHT]

Bookmark: Join points and segments
FeatureJoiner_3
    ATTR_CONFLICT_RES = Use Left
    GEOMETRY_HANDLING = Use Left
    JOIN_KEYS = segment_id segment_id AUTO
    JOIN_MODE = Left
    JOINED -> AttributeManager_4
AttributeManager_4
    ATTR_TABLE:
      REMOVE mode
      SET_TO rails = FME_CONDITIONAL:DEFAULT_VALUE'_FME_NO_OP_'BOOL_OP;OR;COMPOSITE_TEST;1;TEST rails ATTRIBUTE_VALUE_NULL _FME_BLANK_STRING_'false'FME_NUM_CONDITIONS2___
      REMOVE _node_number
      REMOVE _band_b{}.value
      REMOVE OIDN
      REMOVE pre_node_number
      REMOVE _band_a{}.value
    -> Sorter

Bookmark: Remove duplicates
Sorter
    SORT_PARM = segment_id ALPHA ASCENDING rails ALPHA DESCENDING
    SORTED -> DuplicateFilter_2
DuplicateFilter_2
    INPUT_ORDERED_CHOICE = Yes
    KEYATTR = segment_id
    UNIQUE -> Rails (writer CSV2_1)

Bookmark: Write to csv
Rails (writer CSV2_1)
    attributes: segment_id string, rails string
