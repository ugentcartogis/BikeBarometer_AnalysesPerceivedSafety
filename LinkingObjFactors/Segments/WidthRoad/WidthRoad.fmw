FME workspace WidthRoad.fmw

Parameters:
- SourceDataset_SHAPEFILE = C:\Users\Sien Benoit\OneDrive - UGent\Werk_UGent\Doctoraat\Datasets_routes\DataFietsbarometerVL_210402\06_LinkingObjFactors\Segments\dataset_segments_210402_08_infra.shp   # Source Esri Shapefile(s)
- SourceDataset_SHAPEFILE_4 = $(FME_MF_DIR)WidthRoad_projected_width.shp   # Source Esri Shapefile(s)
- DestDataset_CSV2 = C:\Users\Sien Benoit\OneDrive - UGent\Werk_UGent\Doctoraat\Datasets_routes\DataFietsbarometerVL_210402\06_LinkingObjFactors\WidthRoad   # Destination CSV (Comma Separated Value) Folder

Readers:
- SHAPEFILE_1: SHAPEFILE from $(SourceDataset_SHAPEFILE) in EPSG:31370
- SHAPEFILE_3: SHAPEFILE from $(SourceDataset_SHAPEFILE_4)

Writers:
- CSV2_1: CSV2 to $(DestDataset_CSV2)

Note: Segments with the width of the road
WidthRoad_projected_width (reader SHAPEFILE_3)
    attributes: WS_OIDN number(15,0), WS_UIDN char(18), WS_GIDN char(18), B_WK_OIDN number(15,0), E_WK_OIDN number(15,0), STATUS short, LBLSTATUS char(64), MORF short, LBLMORF char(64), WEGCAT char(5), LBLWEGCAT char(64), LSTRNMID number(15,0), LSTRNM char(80), RSTRNMID number(15,0), RSTRNM char(80), BEHEER char(18), LBLBEHEER char(64), METHODE short, LBLMETHOD char(64), OPNDATUM char(15), BEGINTIJD char(15), BEGINORG char(18), LBLBGNORG char(64), TGBEP short, LBLTGBEP char(64), att_WB_OID number(15,0), att_WS_GID char(18), att_BREEDT short, att_VANPOS float, att_TOTPOS float,
      att_BEGINT char(15), att_BEGINO char(18), att_LBLBGN char(64)
    -> Matcher
Note: Delete segments with the same geometry (but possibly in the oppsite direction), and keep the segment with the largest width.
Note: Segments dataset that need additional new attributes
Note: Calculate the azimuth for each segment and delete unnecessary attributes
Note: Find the closest l4 lines within a distance of 10 m
Note: Keep the AIV segment that does not deviate more than 15° from the segment, and which is at the closest distance to the segment
Note: Segments that have no match with a AIV segment (e.g. separate bike paths) get a width of 10 m.
Note: Select and rename the attributes and write to a csv file that can be joined to the original segments shapefile. Roads with a negative width (no road) get a width of 10 m.
dataset_segments_210402_08_infra (reader SHAPEFILE_1)
    attributes: segment_id long, mode char(254)
    -> HorizontalAngleCalculator
    -> ChangeDetector [ORIGINAL]

Bookmark: Delete duplicate geometries
Matcher
    BLANK_AND_MISSING_NAMES_TRAITS_DIFFER = No
    CHECK_COORDINATE_SYSTEMS = No
    CNT_ATTR = _match_id
    LENIENT_MATCH = Yes
    LIST_ATTRS_TO_INCLUDE = att_BREEDT att_WB_OID WS_OIDN
    MATCH = FULL
    SM_LIST_NAME = _idem
    MATCHED -> Sorter
    NOT_MATCHED -> HorizontalAngleCalculator_2
Sorter
    GROUP_BY = _match_id
    SORT_PARM = att_BREEDT NUMERIC DESCENDING
    SORTED -> Sampler
Sampler
    GROUP_BY = _match_id
    RATE = 1
    SAMPLE_MODE = No
    SAMPLE_TYPE_LONG = First N Features
    SAMPLED -> HorizontalAngleCalculator_2

Bookmark: Azimuth calculation
HorizontalAngleCalculator_2
    ANGLE_TYPE = Feature
    UNIT_OUTPUT = DEG
    -> AttributeManager_2
AttributeManager_2
    ATTR_TABLE:
      RENAME_SET_VALUE _azimuth > _azimuth_breedteweg
      REMOVE _X
      REMOVE _Y
      RENAME_SET_VALUE _angle > _angle_breedteweg
      REMOVE _creation_instance
      REMOVE _x
      REMOVE _y
      REMOVE _z
      REMOVE _xEnd
      REMOVE _yEnd
      REMOVE _zEnd
      REMOVE _match_id
      REMOVE WS_UIDN
      REMOVE WS_GIDN
      REMOVE B_WK_OIDN
      REMOVE E_WK_OIDN
      REMOVE STATUS
      REMOVE LBLSTATUS
      REMOVE MORF
      REMOVE LBLMORF
      REMOVE WEGCAT
      REMOVE LBLWEGCAT
      REMOVE LSTRNMID
      REMOVE LSTRNM
      REMOVE RSTRNMID
      REMOVE RSTRNM
      REMOVE BEHEER
      REMOVE LBLBEHEER
      REMOVE METHODE
      REMOVE LBLMETHOD
      REMOVE OPNDATUM
      REMOVE BEGINTIJD
      REMOVE BEGINORG
      REMOVE LBLBGNORG
      REMOVE TGBEP
      REMOVE LBLTGBEP
      REMOVE att_WB_OID
      REMOVE att_WS_GID
      REMOVE att_VANPOS
      REMOVE att_TOTPOS
      REMOVE att_BEGINT
      REMOVE att_BEGINO
      REMOVE att_LBLBGN
    -> NeighborFinder [CANDIDATE]
HorizontalAngleCalculator
    ANGLE_TYPE = Feature
    UNIT_OUTPUT = DEG
    -> AttributeManager
AttributeManager
    ATTR_TABLE:
      RENAME_SET_VALUE _azimuth > _azimuth_segm
      REMOVE _X
      REMOVE _Y
      RENAME_SET_VALUE _angle > _angle_segm
      RENAME_SET_VALUE mode > cycle_infra
      REMOVE _creation_instance
      REMOVE _x
      REMOVE _y
      REMOVE _z
      REMOVE _xEnd
      REMOVE _yEnd
      REMOVE _zEnd
    -> NeighborFinder [BASE]

Bookmark: Find closest line
NeighborFinder
    ATTR_ACCUM_MODE = Merge Candidate
    ATTR_CONFLICT_RES = Use Base
    CANDIDATES_FIRST = No
    CLOSE_LIST_ATTRS_TO_INCLUDE_MODE = All Attributes
    CLOSE_LIST_NAME = allo
    INSERT_VERTEX = No
    K = 4
    MAX = 10
    MEASURES_FROM_CANDIDATE = Yes
    MEASURE_TYPE = Continuous
    MODE = Bases and Candidates
    TREAT_POLYGON_AS = Lines
    MATCHED -> ListExploder
ListExploder
    ATTR_ACCUM_MODE = Merge List Attributes
    ATTR_CONFLICT_RES = Use List Attribute Values
    INDEX_ATTR = _element_index
    LIST_ATTR = allo{}
    ELEMENTS -> TestFilter

Bookmark: Keep the most similar segment
TestFilter
    DEFAULT_VALUE = <UNFILTERED>
    TEST_LIST = "BOOL_OP,AND,COMPOSITE_TEST,""""""1"""""",TEST_CLAUSE,TEST @abs(@fmod(@abs(@Value(_azimuth_segm)-@Value(_azimuth_breedteweg))+180, 360)-180) < 15",@Value(_azimuth_netw) < @fmod(@Value(_azimuth_segm)+10,360),"BOOL_OP,AND,COMPOSITE_TEST,""""""1"""""",TEST_CLAUSE,TEST @abs(@fmod(@abs(@fmod(@Value(_azimuth_segm)+180,360)-@Value(_azimuth_breedteweg))+180, 360)-180) < 15",@Value(_azimuth_netw) < @fmod(@Value(_azimuth_segm)+190,360)
    @Value(_azimuth_netw) < @fmod(@Value(_azimuth_segm)+10,360) -> Sorter_2
    @Value(_azimuth_netw) < @fmod(@Value(_azimuth_segm)+190,360) -> Sorter_2
Sorter_2
    SORT_PARM = distance NUMERIC DESCENDING
    SORTED -> Sampler_2
Sampler_2
    GROUP_BY = segment_id
    RATE = 1
    SAMPLE_MODE = No
    SAMPLE_TYPE_LONG = First N Features
    SAMPLED -> ChangeDetector [REVISED]
    SAMPLED -> AttributeManager_3

Bookmark: Unmatched segments
ChangeDetector
    BLANK_AND_MISSING_NAMES_TRAITS_DIFFER = No
    CHECK_COORDINATE_SYSTEMS = No
    LENIENT_MATCH = Yes
    MATCH = FULL
    UNCHANGED_OUTPUT = Output Original
    DELETED -> AttributeCreator
AttributeCreator
    ATTR_TABLE:
      SET_TO widthroad = 10
      SET_TO aiv_wegsegmentid = NULL
    -> AttributeManager_3

Bookmark: Write to csv
AttributeManager_3
    ATTR_TABLE:
      REMOVE _azimuth_segm
      REMOVE _angle_segm
      REMOVE cycle_infra
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE mode
      REMOVE _azimuth_breedteweg
      REMOVE _angle_breedteweg
      RENAME_SET_VALUE WS_OIDN > aiv_wegsegmentid
      RENAME_SET_VALUE att_BREEDT > widthroad = FME_CONDITIONAL:DEFAULT_VALUE'@Value(widthroad)'BOOL_OP;OR;COMPOSITE_TEST;1;TEST @Value(widthroad) < 0'10'FME_NUM_CONDITIONS2___
      SET_TO widthroad = FME_CONDITIONAL:DEFAULT_VALUE'@Value(widthroad)'BOOL_OP;OR;COMPOSITE_TEST;1;TEST @Value(widthroad) < 0'10'FME_NUM_CONDITIONS2___
    -> WidthRoad (writer CSV2_1)
WidthRoad (writer CSV2_1)
    attributes: segment_id string, aiv_wegsegmentid string, widthroad string
