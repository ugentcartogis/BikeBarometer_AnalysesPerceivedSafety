FME workspace DoubleDir.fmw

Parameters:
- SourceDataset_SHAPEFILE = C:\Users\Sien Benoit\OneDrive - UGent\Werk_UGent\Doctoraat\Datasets_routes\DataFietsbarometerVL_210402\06_LinkingObjFactors\Segments\dataset_segments_210402_08_infra.shp   # Source Esri Shapefile(s)
- SourceDataset_SHAPEFILE_3 = C:\Users\Sien Benoit\OneDrive - UGent\Werk_UGent\Doctoraat\Datasets_environment\doubledirection\TOTAL\DoubleDir_total.shp   # Source Esri Shapefile(s)
- DestDataset_CSV2 = C:\Users\Sien Benoit\OneDrive - UGent\Werk_UGent\Doctoraat\Datasets_routes\DataFietsbarometerVL_210402\06_LinkingObjFactors\Segments\DoubleDir   # Destination CSV (Comma Separated Value) Folder

Readers:
- SHAPEFILE_1: SHAPEFILE from $(SourceDataset_SHAPEFILE) in EPSG:31370
- SHAPEFILE_2: SHAPEFILE from $(SourceDataset_SHAPEFILE_3)

Writers:
- CSV2_1: CSV2 to $(DestDataset_CSV2)

Note: Segments with the double direction of the bike paths in Flanders
DoubleDir_total (reader SHAPEFILE_2)
    attributes: DoubleDir char(200), crc_id char(200)
    -> AttributeCreator_2
Note: Delete segments with the same geometry (but possibly in the oppsite direction), and keep the segment that has a double direction. For this purpose, add an attribute with a number indicating the double direction.
Note: Segments dataset that additional new attributes
Note: Calculate the azimuth for each segment and delete unnecessary attributes
Note: Find the closest 4 lines within a distance of 10 m
Note: Keep the doubledir segment that does not deviate more than 15° from the segment, and which is at the closest distance to the segment
Note: Segments that have no match with a doubledir segment (e.g. separate bike paths) get a NULL value.
Note: Select and rename the attributes and write to a csv file that can be joined to the original segments shapefile.
dataset_segments_210402_08_infra (reader SHAPEFILE_1)
    attributes: segment_id long, mode char(254)
    -> HorizontalAngleCalculator
    -> ChangeDetector [ORIGINAL]

Bookmark: Delete duplicate geometries
AttributeCreator_2
    ATTR_TABLE = SET_TO DoubleDir_nr = FME_CONDITIONAL:DEFAULT_VALUE'@Evaluate(3)'BOOL_OP;OR;COMPOSITE_TEST;1;TEST @Value(DoubleDir) = true'@Evaluate(1)'BOOL_OP;OR;COMPOSITE_TEST;1;TEST @Value(DoubleDir) = false'@Evaluate(2)'FME_NUM_CONDITIONS3___
    -> Matcher
Matcher
    BLANK_AND_MISSING_NAMES_TRAITS_DIFFER = No
    CHECK_COORDINATE_SYSTEMS = No
    CNT_ATTR = _match_id
    LENIENT_MATCH = Yes
    LIST_ATTRS_TO_INCLUDE = crc_id DoubleDir DoubleDir_nr
    MATCH = FULL
    SM_LIST_NAME = _idem
    MATCHED -> Sorter
    NOT_MATCHED -> HorizontalAngleCalculator_2
Sorter
    GROUP_BY = _match_id
    SORT_PARM = DoubleDir_nr NUMERIC ASCENDING
    SORTED -> Sampler
Sampler
    GROUP_BY = _match_id
    RATE = 1
    SAMPLE_MODE = No
    SAMPLE_TYPE_LONG = First N Features
    SAMPLED -> HorizontalAngleCalculator_2

Bookmark: Azimuth calculation
HorizontalAngleCalculator_2
    ANGLE_TYPE = Feature
    UNIT_OUTPUT = DEG
    -> AttributeManager_2
AttributeManager_2
    ATTR_TABLE:
      RENAME_SET_VALUE _azimuth > _azimuth_snelheid
      REMOVE _X
      REMOVE _Y
      RENAME_SET_VALUE _angle > _angle_snelheid
      REMOVE _creation_instance
      REMOVE _x
      REMOVE _y
      REMOVE _z
      REMOVE _xEnd
      REMOVE _yEnd
      REMOVE _zEnd
      REMOVE _match_id
      SET_TO DoubleDir = FME_CONDITIONAL:DEFAULT_VALUE'_FME_NO_OP_'BOOL_OP;OR;COMPOSITE_TEST;1;TEST DoubleDir ATTRIBUTE_IS_MISSING _FME_BLANK_STRING_'FME_NULL_VALUE'FME_NUM_CONDITIONS2___
    -> NeighborFinder [CANDIDATE]
HorizontalAngleCalculator
    ANGLE_TYPE = Feature
    UNIT_OUTPUT = DEG
    -> AttributeManager
AttributeManager
    ATTR_TABLE:
      RENAME_SET_VALUE _azimuth > _azimuth_segm
      REMOVE _X
      REMOVE _Y
      RENAME_SET_VALUE _angle > _angle_segm
      RENAME_SET_VALUE mode > cycle_infra
      REMOVE _creation_instance
      REMOVE _x
      REMOVE _y
      REMOVE _z
      REMOVE _xEnd
      REMOVE _yEnd
      REMOVE _zEnd
    -> NeighborFinder [BASE]

Bookmark: Find closest line
NeighborFinder
    ATTR_ACCUM_MODE = Merge Candidate
    ATTR_CONFLICT_RES = Use Base
    CANDIDATES_FIRST = No
    CLOSE_LIST_ATTRS_TO_INCLUDE_MODE = All Attributes
    CLOSE_LIST_NAME = allo
    INSERT_VERTEX = No
    K = 4
    MAX = 10
    MEASURES_FROM_CANDIDATE = Yes
    MEASURE_TYPE = Continuous
    MODE = Bases and Candidates
    TREAT_POLYGON_AS = Lines
    MATCHED -> ListExploder
ListExploder
    ATTR_ACCUM_MODE = Merge List Attributes
    ATTR_CONFLICT_RES = Use List Attribute Values
    INDEX_ATTR = _element_index
    LIST_ATTR = allo{}
    ELEMENTS -> TestFilter

Bookmark: Keep the most similar segment
TestFilter
    DEFAULT_VALUE = <UNFILTERED>
    TEST_LIST = "BOOL_OP,AND,COMPOSITE_TEST,""""""1"""""",TEST_CLAUSE,TEST @abs(@fmod(@abs(@Value(_azimuth_segm)-@Value(_azimuth_snelheid))+180, 360)-180) < 15",@Value(_azimuth_netw) < @fmod(@Value(_azimuth_segm)+10,360),"BOOL_OP,AND,COMPOSITE_TEST,""""""1"""""",TEST_CLAUSE,TEST @abs(@fmod(@abs(@fmod(@Value(_azimuth_segm)+180,360)-@Value(_azimuth_snelheid))+180, 360)-180) < 15",@Value(_azimuth_netw) < @fmod(@Value(_azimuth_segm)+190,360)
    @Value(_azimuth_netw) < @fmod(@Value(_azimuth_segm)+10,360) -> Sorter_2
    @Value(_azimuth_netw) < @fmod(@Value(_azimuth_segm)+190,360) -> Sorter_2
Sorter_2
    SORT_PARM = distance NUMERIC DESCENDING
    SORTED -> Sampler_2
Sampler_2
    GROUP_BY = segment_id
    RATE = 1
    SAMPLE_MODE = No
    SAMPLE_TYPE_LONG = First N Features
    SAMPLED -> ChangeDetector [REVISED]
    SAMPLED -> AttributeManager_3

Bookmark: Unmatched segments
ChangeDetector
    BLANK_AND_MISSING_NAMES_TRAITS_DIFFER = No
    CHECK_COORDINATE_SYSTEMS = No
    LENIENT_MATCH = Yes
    MATCH = FULL
    UNCHANGED_OUTPUT = Output Original
    DELETED -> AttributeCreator
AttributeCreator
    ATTR_TABLE:
      SET_TO DoubleDir = FME_NULL_VALUE
      SET_TO crc_id = FME_NULL_VALUE
    -> AttributeManager_3

Bookmark: Write to csv
AttributeManager_3
    ATTR_TABLE:
      REMOVE _azimuth_segm
      REMOVE _angle_segm
      REMOVE cycle_infra
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE mode
      REMOVE _azimuth_snelheid
      REMOVE _angle_snelheid
      REMOVE crc_id
      REMOVE DoubleDir_nr
    -> DoubleDir (writer CSV2_1)
DoubleDir (writer CSV2_1)
    attributes: segment_id string, DoubleDir string
