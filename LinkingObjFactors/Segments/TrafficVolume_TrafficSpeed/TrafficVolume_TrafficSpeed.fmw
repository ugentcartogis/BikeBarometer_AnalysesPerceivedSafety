FME workspace TrafficVolume_TrafficSpeed.fmw

Parameters:
- SourceDataset_SHAPEFILE = C:\Users\Sien Benoit\OneDrive - UGent\Werk_UGent\Doctoraat\Datasets_routes\DataFietsbarometerVL_210402\06_LinkingObjFactors\Segments\dataset_segments_210402_08_infra.shp   # Source Esri Shapefile(s)
- SourceDataset_SHAPEFILE_3 = $(FME_MF_DIR)network_projected_trafficdata.shp   # Source Esri Shapefile(s)
- DestDataset_CSV2 = C:\Users\Sien Benoit\OneDrive - UGent\Werk_UGent\Doctoraat\Datasets_routes\DataFietsbarometerVL_210402\06_LinkingObjFactors\TrafficVolume_TrafficSpeed   # Destination CSV (Comma Separated Value) Folder

Readers:
- SHAPEFILE_1: SHAPEFILE from $(SourceDataset_SHAPEFILE) in EPSG:31370
- SHAPEFILE_2: SHAPEFILE from $(SourceDataset_SHAPEFILE_3) in EPSG:31370

Writers:
- CSV2_1: CSV2 to $(DestDataset_CSV2)

Note: TomTom segments that provide new attributes
network_projected_trafficdata (reader SHAPEFILE_2)
    attributes: Id number(19,0), Segment_Id char(20), NewSegId char(40), Length double, FRC number(19,0), SpeedLimit number(19,0), StreetName char(100), BS_AvgTt double, BS_MedTt double, BS_ratio double, BS_AvgSp double, BS_HvgSp double, BS_MedSp double, BS_SdSp double, BS_Hits number(20,0), BS_P5sp number(20,0), BS_P10sp number(20,0), BS_P15sp number(20,0), BS_P20sp number(20,0), BS_P25sp number(20,0), BS_P30sp number(20,0), BS_P35sp number(20,0), BS_P40sp number(20,0), BS_P45sp number(20,0), BS_P50sp number(20,0), BS_P55sp number(20,0), BS_P60sp number(20,0), BS_P65sp number(20,0), BS_P70sp number(20,0), BS_P75sp number(20,0),
      BS_P80sp number(20,0), BS_P85sp number(20,0), BS_P90sp number(20,0), BS_P95sp number(20,0)
    -> Matcher
Note: Delete segments with the same geometry but in the opposite direction, and keep the segment with the highest traffic volume
Note: Segments dataset that needs additional new attributes
Note: Calculate the azimuth for each segment and delete unnecessary attributes
Note: Find the closest l4 lines within a distance of 10 m
Note: Keep the TomTom segment that does not deviate more than 15° from the segment, and which is at the closest distance to the segment
Note: Segments that have no match with a TomTom segment (e.g. separate bike paths) get a traffic volume number of 0 and a traffic speed of 0 km/h.
Note: Select and rename the attributes and write to a csv file that can be joined to the original segments shapefile.
dataset_segments_210402_08_infra (reader SHAPEFILE_1)
    attributes: segment_id long, mode char(254)
    -> HorizontalAngleCalculator
    -> ChangeDetector [ORIGINAL]

Bookmark: Delete duplicate geometries
Matcher
    BLANK_AND_MISSING_NAMES_TRAITS_DIFFER = No
    CHECK_COORDINATE_SYSTEMS = No
    CNT_ATTR = _match_id
    LENIENT_MATCH = Yes
    LIST_ATTRS_TO_INCLUDE = BS_AvgSp BS_AvgTt BS_Hits FRC Id Length NewSegId Segment_Id SpeedLimit StreetName
    MATCH = FULL
    SM_LIST_NAME = _idem
    MATCHED -> Sorter
    NOT_MATCHED -> HorizontalAngleCalculator_2
Sorter
    GROUP_BY = _match_id
    SORT_PARM = BS_Hits NUMERIC DESCENDING
    SORTED -> Sampler
Sampler
    GROUP_BY = _match_id
    RATE = 1
    SAMPLE_MODE = No
    SAMPLE_TYPE_LONG = First N Features
    SAMPLED -> HorizontalAngleCalculator_2

Bookmark: Azimuth calculation
HorizontalAngleCalculator_2
    ANGLE_TYPE = Feature
    UNIT_OUTPUT = DEG
    -> AttributeManager_2
AttributeManager_2
    ATTR_TABLE:
      RENAME_SET_VALUE _azimuth > _azimuth_netw
      REMOVE _X
      REMOVE _Y
      RENAME_SET_VALUE _angle > _angle_netw
      REMOVE Segment_Id
      REMOVE NewSegId
      REMOVE BS_AvgTt
      REMOVE BS_MedTt
      REMOVE BS_ratio
      REMOVE BS_HvgSp
      REMOVE BS_MedSp
      REMOVE BS_SdSp
      REMOVE BS_P5sp
      REMOVE BS_P10sp
      REMOVE BS_P15sp
      REMOVE BS_P20sp
      REMOVE BS_P25sp
      REMOVE BS_P30sp
      REMOVE BS_P35sp
      REMOVE BS_P40sp
      REMOVE BS_P45sp
      REMOVE BS_P50sp
      REMOVE BS_P55sp
      REMOVE BS_P60sp
      REMOVE BS_P65sp
      REMOVE BS_P70sp
      REMOVE BS_P75sp
      REMOVE BS_P80sp
      REMOVE BS_P85sp
      REMOVE BS_P90sp
      REMOVE BS_P95sp
      REMOVE _creation_instance
      REMOVE _x
      REMOVE _y
      REMOVE _z
      REMOVE _xEnd
      REMOVE _yEnd
      REMOVE _zEnd
    -> NeighborFinder [CANDIDATE]
HorizontalAngleCalculator
    ANGLE_TYPE = Feature
    UNIT_OUTPUT = DEG
    -> AttributeManager
AttributeManager
    ATTR_TABLE:
      RENAME_SET_VALUE _azimuth > _azimuth_segm
      REMOVE _X
      REMOVE _Y
      RENAME_SET_VALUE _angle > _angle_segm
      RENAME_SET_VALUE mode > cycle_infra
      REMOVE _creation_instance
      REMOVE _x
      REMOVE _y
      REMOVE _z
      REMOVE _xEnd
      REMOVE _yEnd
      REMOVE _zEnd
    -> NeighborFinder [BASE]

Bookmark: Find closest line
NeighborFinder
    ATTR_ACCUM_MODE = Merge Candidate
    ATTR_CONFLICT_RES = Use Base
    CANDIDATES_FIRST = No
    CLOSE_LIST_ATTRS_TO_INCLUDE_MODE = All Attributes
    CLOSE_LIST_NAME = allo
    INSERT_VERTEX = No
    K = 4
    MAX = 10
    MEASURES_FROM_CANDIDATE = Yes
    MEASURE_TYPE = Continuous
    MODE = Bases and Candidates
    TREAT_POLYGON_AS = Lines
    MATCHED -> ListExploder
ListExploder
    ATTR_ACCUM_MODE = Merge List Attributes
    ATTR_CONFLICT_RES = Use List Attribute Values
    INDEX_ATTR = _element_index
    LIST_ATTR = allo{}
    ELEMENTS -> TestFilter

Bookmark: Keep the most similar segment
TestFilter
    DEFAULT_VALUE = <UNFILTERED>
    TEST_LIST = "BOOL_OP,AND,COMPOSITE_TEST,""""""1"""""",TEST_CLAUSE,TEST @abs(@fmod(@abs(@Value(_azimuth_segm)-@Value(_azimuth_netw))+180, 360)-180) < 15",@Value(_azimuth_netw) < @fmod(@Value(_azimuth_segm)+10,360),"BOOL_OP,AND,COMPOSITE_TEST,""""""1"""""",TEST_CLAUSE,TEST @abs(@fmod(@abs(@fmod(@Value(_azimuth_segm)+180,360)-@Value(_azimuth_netw))+180, 360)-180) < 15",@Value(_azimuth_netw) < @fmod(@Value(_azimuth_segm)+190,360)
    @Value(_azimuth_netw) < @fmod(@Value(_azimuth_segm)+10,360) -> Sorter_2
    @Value(_azimuth_netw) < @fmod(@Value(_azimuth_segm)+190,360) -> Sorter_2
Sorter_2
    SORT_PARM = distance NUMERIC DESCENDING
    SORTED -> Sampler_2
Sampler_2
    GROUP_BY = segment_id
    RATE = 1
    SAMPLE_MODE = No
    SAMPLE_TYPE_LONG = First N Features
    SAMPLED -> ChangeDetector [REVISED]
    SAMPLED -> AttributeManager_3

Bookmark: Unmatched segments
ChangeDetector
    BLANK_AND_MISSING_NAMES_TRAITS_DIFFER = No
    CHECK_COORDINATE_SYSTEMS = No
    LENIENT_MATCH = Yes
    MATCH = FULL
    UNCHANGED_OUTPUT = Output Original
    DELETED -> AttributeCreator
AttributeCreator
    ATTR_TABLE:
      SET_TO BS_AvgSp = 0
      SET_TO BS_Hits = 0
      SET_TO Id = NULL
    -> AttributeManager_3

Bookmark: Write to csv
AttributeManager_3
    ATTR_TABLE:
      REMOVE _azimuth_segm
      REMOVE _angle_segm
      REMOVE cycle_infra
      REMOVE _azimuth_netw
      REMOVE _angle_netw
      RENAME_SET_VALUE Id > tomtom_id
      REMOVE Length
      REMOVE FRC
      REMOVE SpeedLimit
      REMOVE StreetName
      RENAME_SET_VALUE BS_AvgSp > TrafficSpeed
      RENAME_SET_VALUE BS_Hits > TrafficVolume
      REMOVE _match_id
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE mode
    -> TrafficVolume_TrafficSpeed (writer CSV2_1)
TrafficVolume_TrafficSpeed (writer CSV2_1)
    attributes: segment_id string, tomtom_id string, TrafficSpeed string, TrafficVolume string
