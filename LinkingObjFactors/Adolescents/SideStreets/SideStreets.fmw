FME workspace SideStreets.fmw

Parameters:
- SourceDataset_SHAPEFILE = C:\Users\Sien Benoit\OneDrive - UGent\Werk_UGent\Doctoraat\Datasets_routes\DataFietsbarometerVL_210402\06_LinkingObjFactors\Adolescents\dataset_adolescents_210402_08_total.shp   # Source Esri Shapefile(s)
- SourceDataset_SHAPEFILE_3 = C:\Users\Sien Benoit\OneDrive - UGent\Werk_UGent\Doctoraat\Datasets_environment\sidestreets\roads_vlaanderen_nodes_2020_2021.shp   # Source Esri Shapefile(s)
- DestDataset_CSV2 = C:\Users\Sien Benoit\OneDrive - UGent\Werk_UGent\Doctoraat\Datasets_routes\DataFietsbarometerVL_210402\06_LinkingObjFactors\Adolescents\SideStreets   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Nodes where roads intersect in the road network of Flanders (2020-2021)
Note: Find which points lie on which lines and remove unnecessary attributes.
Note: Keep only one record per student id and sum the number of points for lines that cross but are of the same student.
Note: Write to a csv file that can be joined to the original routes shapefile.
roads_vlaanderen_nodes_2020_2021 (reader SHAPEFILE_2)
    attributes: node_id long
    -> PointOnLineOverlayer [POINT]
Note: Routes of the adolescents that need additional attributes
dataset_adolescents_210402_08_total (reader SHAPEFILE_1)
    attributes: student_id long, gender char(254), age long, class_nam char(254), class_grad long, school_id long, school_nam char(254), municipal char(254), postal_cod long, start_time char(254), end_time char(254), dur long, freq_sc double, rt_t_dist double, rt_t_dm char(254), rt_a_dist double, rt_a_infra char(254), rt_a_dm char(254), rt_a_cycl short, ov_saf_sc long, det_short short, det_least short, det_slow short, det_infra short, det_beau short, det_obs short, det_oths short, det_shop short, det_oth short, comp_nr long
    -> PointOnLineOverlayer [LINE]

Bookmark: Find points on lines
PointOnLineOverlayer
    DEAGGREGATE_INPUT = Yes
    MEASURE_TYPE = Continuous
    MERGE_MEASURES = Yes
    OV_ATTR = _overlaps
    TOLERANCE = 0
    LINE -> AttributeManager
AttributeManager
    ATTR_TABLE:
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
      RENAME_SET_VALUE _overlaps > SideStreets
    -> DuplicateFilter

Bookmark: Remove duplicate rows and aggregate remaining parts
DuplicateFilter
    INPUT_ORDERED_CHOICE = No
    KEYATTR = student_id SideStreets
    UNIQUE -> Aggregator
Aggregator
    ACCUM_ATTRS_NAME = Use Attributes From One Feature
    AGGREGATE_TYPE = Homogeneous Collection (If Possible)
    GROUP_BY = student_id
    MODE = Geometry - Assemble One Level
    SEP = ,
    SUM = SideStreets
    AGGREGATE -> SideStreets (writer CSV2_1)

Bookmark: Write to csv
SideStreets (writer CSV2_1)
    attributes: student_id string, SideStreets string
