FME workspace Width.fmw

Parameters:
- SourceDataset_SHAPEFILE = C:\Users\Sien Benoit\OneDrive - UGent\Werk_UGent\Doctoraat\Datasets_routes\DataFietsbarometerVL_210402\06_LinkingObjFactors\Adolescents\routesegments_2020_2021.shp   # Source Esri Shapefile(s)
- SourceDataset_SHAPEFILE_3 = C:\Users\Sien Benoit\OneDrive - UGent\Werk_UGent\Doctoraat\Datasets_environment\width\TOTAL\Width_total.shp   # Source Esri Shapefile(s)
- DestDataset_CSV2 = C:\Users\Sien Benoit\OneDrive - UGent\Werk_UGent\Doctoraat\Datasets_routes\DataFietsbarometerVL_210402\06_LinkingObjFactors\Adolescents\Width   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Segments of the routes of the adolescents that need additional attributes
Note: Calculate the azimuth for each segment and delete unnecessary attributes. If the width of a segment is larger than 5 m (500 cm), set the width to 2 m (200 cm) because this is probably a mistake in the data collection.
Note: Find the closest 4 lines within a distance of 10 m
Note: Keep the width segment that does not deviate more than 15° from the segment, and which is at the closest distance to the segment
Note: Segments that have no match with a width segment (e.g. separate bike paths) get a NULL value.
Note: Join all segments back together and select only the necessary attributes.
Note: Calculate the average width of the bike paths along the route (group segments by student id), weighted by the length of each segment.
Note: Select and rename the attributes and write to a csv file that can be joined to the original routes shapefile.
routesegments_2020_2021 (reader SHAPEFILE_1)
    attributes: student_id long, edge_id long, direction long, start_node long, end_node long
    -> HorizontalAngleCalculator
    -> ChangeDetector [ORIGINAL]
Note: Segments with the width of the bike paths in Flanders
Note: Delete segments with the same geometry but in the opposite direction, and keep the segment with the widest bike path.
Width_total (reader SHAPEFILE_2)
    attributes: width char(200), crc_id char(200)
    -> Matcher

Bookmark: Azimuth calculation
HorizontalAngleCalculator
    ANGLE_TYPE = Feature
    UNIT_OUTPUT = DEG
    -> AttributeManager
AttributeManager
    ATTR_TABLE:
      RENAME_SET_VALUE _azimuth > _azimuth_segm
      REMOVE _X
      REMOVE _Y
      RENAME_SET_VALUE _angle > _angle_segm
      REMOVE _creation_instance
      REMOVE _x
      REMOVE _y
      REMOVE _z
      REMOVE _xEnd
      REMOVE _yEnd
      REMOVE _zEnd
      REMOVE direction
      REMOVE start_node
      REMOVE end_node
    -> NeighborFinder [BASE]
HorizontalAngleCalculator_2
    ANGLE_TYPE = Feature
    UNIT_OUTPUT = DEG
    -> AttributeManager_2
AttributeManager_2
    ATTR_TABLE:
      RENAME_SET_VALUE _azimuth > _azimuth_netw
      REMOVE _X
      REMOVE _Y
      RENAME_SET_VALUE _angle > _angle_snelheid
      REMOVE _creation_instance
      REMOVE _x
      REMOVE _y
      REMOVE _z
      REMOVE _xEnd
      REMOVE _yEnd
      REMOVE _zEnd
      REMOVE _match_id
      SET_TO width = FME_CONDITIONAL:DEFAULT_VALUE'_FME_NO_OP_'BOOL_OP;OR;COMPOSITE_TEST;1;TEST @Value(width) > @Evaluate(500)'@Evaluate(200)'FME_NUM_CONDITIONS2___
    -> NeighborFinder [CANDIDATE]

Bookmark: Delete duplicate geometries
Matcher
    BLANK_AND_MISSING_NAMES_TRAITS_DIFFER = No
    CHECK_COORDINATE_SYSTEMS = No
    CNT_ATTR = _match_id
    LENIENT_MATCH = Yes
    LIST_ATTRS_TO_INCLUDE = crc_id width
    MATCH = FULL
    SM_LIST_NAME = _idem
    MATCHED -> Sorter
    NOT_MATCHED -> HorizontalAngleCalculator_2
Sorter
    GROUP_BY = _match_id
    SORT_PARM = width NUMERIC DESCENDING
    SORTED -> Sampler
Sampler
    GROUP_BY = _match_id
    RATE = 1
    SAMPLE_MODE = No
    SAMPLE_TYPE_LONG = First N Features
    SAMPLED -> HorizontalAngleCalculator_2

Bookmark: Find closest line
NeighborFinder
    ATTR_ACCUM_MODE = Merge Candidate
    ATTR_CONFLICT_RES = Use Base
    CANDIDATES_FIRST = No
    CLOSE_LIST_ATTRS_TO_INCLUDE_MODE = All Attributes
    CLOSE_LIST_NAME = allo
    INSERT_VERTEX = No
    K = 4
    MAX = 10
    MEASURES_FROM_CANDIDATE = Yes
    MEASURE_TYPE = Continuous
    MODE = Bases and Candidates
    TREAT_POLYGON_AS = Lines
    MATCHED -> ListExploder
ListExploder
    ATTR_ACCUM_MODE = Merge List Attributes
    ATTR_CONFLICT_RES = Use List Attribute Values
    INDEX_ATTR = _element_index
    LIST_ATTR = allo{}
    ELEMENTS -> TestFilter

Bookmark: Keep the most similar segment
TestFilter
    DEFAULT_VALUE = <UNFILTERED>
    TEST_LIST = "BOOL_OP,AND,COMPOSITE_TEST,""""""1"""""",TEST_CLAUSE,TEST @abs(@fmod(@abs(@Value(_azimuth_segm)-@Value(_azimuth_netw))+180, 360)-180) < 15",@Value(_azimuth_netw) < @fmod(@Value(_azimuth_segm)+10,360),"BOOL_OP,AND,COMPOSITE_TEST,""""""1"""""",TEST_CLAUSE,TEST @abs(@fmod(@abs(@fmod(@Value(_azimuth_segm)+180,360)-@Value(_azimuth_netw))+180, 360)-180) < 15",@Value(_azimuth_netw) < @fmod(@Value(_azimuth_segm)+190,360)
    @Value(_azimuth_netw) < @fmod(@Value(_azimuth_segm)+10,360) -> Sorter_2
    @Value(_azimuth_netw) < @fmod(@Value(_azimuth_segm)+190,360) -> Sorter_2
Sorter_2
    SORT_PARM = distance NUMERIC DESCENDING
    SORTED -> Sampler_2
Sampler_2
    GROUP_BY = edge_id student_id
    RATE = 1
    SAMPLE_MODE = No
    SAMPLE_TYPE_LONG = First N Features
    SAMPLED -> ChangeDetector [REVISED]
    SAMPLED -> AttributeManager_3

Bookmark: Unmatched segments
ChangeDetector
    BLANK_AND_MISSING_NAMES_TRAITS_DIFFER = No
    CHECK_COORDINATE_SYSTEMS = No
    LENIENT_MATCH = Yes
    MATCH = FULL
    UNCHANGED_OUTPUT = Output Original
    DELETED -> AttributeCreator
AttributeCreator
    ATTR_TABLE:
      SET_TO width = FME_NULL_VALUE
      SET_TO crc_id = FME_NULL_VALUE
    -> AttributeManager_3

Bookmark: Join segments
AttributeManager_3
    ATTR_TABLE:
      REMOVE _azimuth_segm
      REMOVE _angle_segm
      REMOVE _azimuth_netw
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE direction
      REMOVE start_node
      REMOVE end_node
      REMOVE _angle_snelheid
    -> LengthCalculator

Bookmark: Calculate the weighted average of the variables
LengthCalculator
    DIM = 2
    LEN_ATTR = length_segment
    MULT = 1
    -> AttributeManager_6
AttributeManager_6
    ATTR_TABLE:
      REMOVE edge_id
      SET_TO length_segment = FME_CONDITIONAL:DEFAULT_VALUE'_FME_NO_OP_'BOOL_OP;OR;COMPOSITE_TEST;1;TEST Condition ATTRIBUTE_VALUE_NULL _FME_BLANK_STRING_'FME_NULL_VALUE'FME_NUM_CONDITIONS2___
      SET_TO Width_Length = @Evaluate(@Value(width)*@Value(length_segment))
    -> Aggregator
Aggregator
    ACCUM_ATTRS_NAME = Use Attributes From One Feature
    AGGREGATE_TYPE = Homogeneous Collection (If Possible)
    GROUP_BY = student_id
    MODE = Geometry - Assemble One Level
    SEP = ,
    SUM = length_segment Width_Length
    AGGREGATE -> AttributeManager_4
AttributeManager_4
    ATTR_TABLE = SET_TO width = @Evaluate(@round(@Value(Width_Length)/@Value(length_segment),0))
    -> AttributeManager_5

Bookmark: Write to csv
AttributeManager_5
    ATTR_TABLE:
      REMOVE length_segment
      REMOVE crc_id
      REMOVE Width_Length
    -> Width (writer CSV2_1)
Width (writer CSV2_1)
    attributes: student_id string, width string
