FME workspace Landuse.fmw

Parameters:
- SourceDataset_SHAPEFILE = C:\Users\Sien Benoit\OneDrive - UGent\Werk_UGent\Doctoraat\Datasets_routes\DataFietsbarometerVL_210402\06_LinkingObjFactors\Adolescents\routesegments_2020_2021.shp   # Source Esri Shapefile(s)
- DestDataset_CSV2 = C:\Users\Sien Benoit\OneDrive - UGent\Werk_UGent\Doctoraat\Datasets_routes\DataFietsbarometerVL_210402\06_LinkingObjFactors\Adolescents\Landuse   # Destination CSV (Comma Separated Value) Folder
- SourceDataset_GEOTIFF = C:\Users\Sien Benoit\OneDrive - UGent\Werk_UGent\Doctoraat\Datasets_environment\landuse\lu_landgebruik_vlaa_2019_v2_clipped.tif   # Source GeoTIFF File(s)

Readers:
- SHAPEFILE_1: SHAPEFILE from $(SourceDataset_SHAPEFILE)
- GEOTIFF_1: GEOTIFF from $(SourceDataset_GEOTIFF)

Writers:
- CSV2_1: CSV2 to $(DestDataset_CSV2)

Note: Geotiff of land use in Flanders (clipped to the routes).
GEOTIFF (reader GEOTIFF_1)
    -> RasterBandNodataSetter
Note: Convert all raster cells to vector points and assign the band value to a new attribute 'landuse_cat'.
Note: Remove all points that have category 5 (transport infrastructure).
Note: Find the most occuring value for land use in each buffer. Remove unnecessary attributes and remove duplicate records.
Note: Join the assigned land use category back to the original segments instead of to their buffer.
Note: Remove unnecessary attributes. Aggregate the segments of each student and sum the lengths of each land use type for each student.
Note: Calculate the length of the complete route and use this to calculate the proportion of each land use type for each route.
Note: Remove unnecessary attributes and write the data to a csv file that can be joined to the original shapefile of the routes.
RasterBandNodataSetter
    NODATA_VALUE = -9999
    REPLACE_CELL_VALUES = No
    -> RasterCellCoercer
Note: Segments of the routes of the adolescents that need additional attributes
Note: Remove unnecessary segments and create a buffer of 25 m around every segment, with straight ends.
Note: Filter on each land use type and calculate the length of the segments of each type.
routesegments_2020_2021 (reader SHAPEFILE_1)
    attributes: student_id long, edge_id long, direction long, start_node long, end_node long
    -> AttributeManager

Bookmark: Convert the raster to point values in a grid.
RasterCellCoercer
    CELL_GEOMETRY = Points
    EXTRACT_BAND_VALUES_AS = Attributes
    EXTRACT_NODATA = No
    PRESERVE_ATTRIBUTES = Yes
    -> AttributeManager_2
AttributeManager_2
    ATTR_TABLE:
      REMOVE _band{}.palette{}.value
      SET_TO landuse = @Value(_band{0}.value)
    -> AttributeManager_3
AttributeManager_3
    ATTR_TABLE:
      REMOVE fme_basename
      REMOVE _band{}.value
    -> Tester

Bookmark: Remove transport category
Tester
    BOOL_OP = OR
    COMPOSITE_TEST = 1
    TEST_CLAUSE = TEST @Value(landuse) != 5
    TEST_MODE = TEST
    PASSED -> PointOnAreaOverlayer [POINT]

Bookmark: Buffer the segments
AttributeManager
    ATTR_TABLE:
      REMOVE direction
      REMOVE start_node
      REMOVE end_node
    -> Bufferer
    -> FeatureJoiner [LEFT]
Bufferer
    ANGLE = 22.5
    CAP_STYLE = None
    CORNER_STYLE = Bevel
    MODE = AREA
    OFFSET = 25
    OFFSET_UNITS = NONE
    BUFFERED -> PointOnAreaOverlayer [AREA]

Bookmark: Find the modal value of the land use category in each buffer.
PointOnAreaOverlayer
    CANDIDATE_LIST_ATTRS_TO_INCLUDE = landuse
    CANDIDATE_LIST_ATTRS_TO_INCLUDE_MODE = Selected Attributes
    CANDIDATE_LIST_NAME = list
    DEAGGREGATE_INPUT = Yes
    OV_ATTR = _overlaps
    POLYS_FIRST = NO
    AREA -> ListStatisticsCalculator
ListStatisticsCalculator
    LIST_ATTR = list{}.landuse
    PREFIX = stats_
    -> AttributeManager_4
AttributeManager_4
    ATTR_TABLE:
      REMOVE list{}.landuse
      REMOVE _overlaps
      REMOVE stats_min
      REMOVE stats_max
      REMOVE stats_median
      REMOVE stats_count
      REMOVE stats_sum
      REMOVE stats_range
      REMOVE stats_mean
      REMOVE stats_stdev
      REMOVE stats_stdevp
      RENAME_SET_VALUE stats_mode > landuse_cat
    -> DuplicateFilter
DuplicateFilter
    INPUT_ORDERED_CHOICE = No
    KEYATTR = landuse_cat edge_id student_id
    UNIQUE -> FeatureJoiner [RIGHT]

Bookmark: Join to the segments
FeatureJoiner
    ATTR_CONFLICT_RES = Use Left
    GEOMETRY_HANDLING = Use Left
    JOIN_KEYS = student_id student_id AUTO edge_id edge_id AUTO
    JOIN_MODE = Inner
    JOINED -> Tester_residential
    JOINED -> Tester_industrial
    JOINED -> Tester_commercial
    JOINED -> Tester_recreational
    JOINED -> Tester_agricultural
    JOINED -> Tester_natural

Bookmark: Find the length of each segment with a certain land use type.
Tester_residential
    BOOL_OP = OR
    COMPOSITE_TEST = 1
    TEST_CLAUSE = TEST @Value(landuse_cat) IN 1,8
    TEST_MODE = TEST
    PASSED -> LengthCalculator
LengthCalculator
    DIM = 2
    LEN_ATTR = length_residential
    MULT = 1
    -> AttributeManager_5
Tester_industrial
    BOOL_OP = OR
    COMPOSITE_TEST = 1
    TEST_CLAUSE = TEST @Value(landuse_cat) IN 2,10,11
    TEST_MODE = TEST
    PASSED -> LengthCalculator_2
LengthCalculator_2
    DIM = 2
    LEN_ATTR = length_industrial
    MULT = 1
    -> AttributeManager_5
Tester_commercial
    BOOL_OP = OR
    COMPOSITE_TEST = 1
    TEST_CLAUSE = TEST @Value(landuse_cat) IN 3,4
    TEST_MODE = TEST
    PASSED -> LengthCalculator_3
LengthCalculator_3
    DIM = 2
    LEN_ATTR = length_commercial
    MULT = 1
    -> AttributeManager_5
Tester_recreational
    BOOL_OP = OR
    COMPOSITE_TEST = 1
    TEST_CLAUSE = TEST @Value(landuse_cat) IN 6
    TEST_MODE = TEST
    PASSED -> LengthCalculator_4
LengthCalculator_4
    DIM = 2
    LEN_ATTR = length_recreational
    MULT = 1
    -> AttributeManager_5
Tester_agricultural
    BOOL_OP = OR
    COMPOSITE_TEST = 1
    TEST_CLAUSE = TEST @Value(landuse_cat) IN 7,9,13,14
    TEST_MODE = TEST
    PASSED -> LengthCalculator_5
LengthCalculator_5
    DIM = 2
    LEN_ATTR = length_agricultural
    MULT = 1
    -> AttributeManager_5
Tester_natural
    BOOL_OP = OR
    COMPOSITE_TEST = 1
    TEST_CLAUSE = TEST @Value(landuse_cat) IN 12,15,16,17,18
    TEST_MODE = TEST
    PASSED -> LengthCalculator_6
LengthCalculator_6
    DIM = 2
    LEN_ATTR = length_natural
    MULT = 1
    -> AttributeManager_5

Bookmark: Merge all segments back to the routes.
AttributeManager_5
    -> Aggregator
Aggregator
    ACCUM_ATTRS_NAME = Use Attributes From One Feature
    AGGREGATE_TYPE = Homogeneous Collection (If Possible)
    GROUP_BY = student_id
    MODE = Geometry - Assemble One Level
    SEP = ,
    SUM = length_agricultural length_commercial length_recreational length_industrial length_natural length_residential
    AGGREGATE -> LengthCalculator_7

Bookmark: Calculate the proportion of each land use type.
LengthCalculator_7
    DIM = 2
    LEN_ATTR = length_total
    MULT = 1
    -> AttributeCreator
AttributeCreator
    ATTR_TABLE:
      SET_TO residential = @Evaluate(@Value(length_residential)/@Value(length_total))
      SET_TO industrial = @Evaluate(@Value(length_industrial)/@Value(length_total))
      SET_TO commercial = @Evaluate(@Value(length_commercial)/@Value(length_total))
      SET_TO recreational = @Evaluate(@Value(length_recreational)/@Value(length_total))
      SET_TO agricultural = @Evaluate(@Value(length_agricultural)/@Value(length_total))
      SET_TO natural = @Evaluate(@Value(length_natural)/@Value(length_total))
    -> AttributeManager_6

Bookmark: Write to csv.
AttributeManager_6
    ATTR_TABLE:
      REMOVE length_natural
      REMOVE length_residential
      REMOVE length_commercial
      REMOVE length_recreational
      REMOVE length_agricultural
      REMOVE length_industrial
      REMOVE edge_id
      REMOVE landuse_cat
      REMOVE length_total
    -> Landuse (writer CSV2_1)
Landuse (writer CSV2_1)
    attributes: residential string, industrial string, commercial string, recreational string, agricultural string, natural string, student_id string

FME custom transformer ListStatisticsCalculator
Calculates fundamental statistics of element values in the specified list, and adds attributes storing the calculation results to the feature.
    Only decimal numbers can be accepted as the list elements. 0 at the head of an element will be ignored. 
    If the incoming feature does not have list attribute with the specified name, or the list contains one or more non-numeric elements, then the feature will be output from the 
    <Rejected>
    port.
    Every rejected feature will have an attribute named "_liststats_error", which contains a text describing the rejected reason. 
    This transformer contains a Python script, which was tested with both Python 2.7 interpreter and 3.6 interpreter.
Parameters
    List Attribute
    :
    Specify a list name which contains numeric elements.
    Prefix of Statistics Attributes
    :
    Specify a common prefix which should be added to names of result attributes. This can be set to empty string, if unnecessary.
    Output features will have these attributes if you specify "stats_" to this parameter.
    -----
    stats_min - The minimum value in all the values. 
    stats_max - The maximum value in all the values. 
    stats_median - The middle value of all the values. 
    stats_count - The number of the elements. 
    stats_sum - The sum of all the values. 
    stats_range - The difference between the minimum and the maximum. i.e. equals to the maximum minus the minimum. 
    stats_mean - The average of all the values. 
    stats_stdev - The standard deviation (sample) of all the values. This will be empty if the number of elements is equal to 1.
    stats_stdevp - The standard deviation (population) of all the values. 
    stats_mode - The most frequent of all the values. If two or more values occur with the highest frequency, one of them will be returned randomly. 
    -----

Parameters:
- LIST_ATTR =   # " " List Attribute
- PREFIX = stats_   # TYPE:varchar(200) Prefix of Statistics Attributes

Input (input)
    -> ParameterFetcher
ParameterFetcher
    ATTR_LIST = liststatisticscalculator.list_attr {$(LIST_ATTR)}
    -> PythonCaller
PythonCaller
    NEW_ATTRIBUTES = min.liststatisticscalculator max.liststatisticscalculator median.liststatisticscalculator count.liststatisticscalculator sum.liststatisticscalculator range.liststatisticscalculator mean.liststatisticscalculator stdev.liststatisticscalculator stdevp.liststatisticscalculator mode.liststatisticscalculator liststatisticscalculator.histogram{}.count liststatisticscalculator.histogram{}.value liststatisticscalculator.flag
    PYTHONSOURCE:
      # 2018-06-14, Takashi Iijime, Updated to support Python 3.x interpreter.
      # 2016-06-24, Takashi Iijima, Added stdevp - standard deviation (population).
      # 2014-08-02, Takashi Iijima, Original Implementation

      import fmeobjects, locale, re, math

      class ListStatisticsCalculator(object):
          def __init__(self):
              import platform
              if platform.python_version_tuple()[0] == '2':
                  loc = locale.getdefaultlocale()
                  enc = loc[1] if loc else 'utf_8'
                  self.toStr = lambda s: s.encode(enc) if isinstance(s, unicode) else s
              else:
                  self.toStr = lambda s: s

          def input(self, feature):
              try:
                  listName = self.toStr(feature.getAttribute('liststatisticscalculator.list_attr'))
                  m = re.match(r'^(.+)\{\}(.*)$', listName)

                  front, index, back = m.group(1), 0, m.group(2)
                  values, total, histogram = [], 0.0, {}
                  while True:
                      v = feature.getAttribute('%s{%d}%s' % (front, index, back))
                      if v == None:
                          break
                      v = float(v)
                      values.append(v)
                      total += v
                      histogram[v] = histogram.setdefault(v, 0) + 1
                      index += 1

                  # Number of elements.
                  count = len(values)
                  if count < 1:
                      raise Exception('could not find valid element')
                  values.sort() # ascending sort

                  # Calculate median, average (mean) and standard deviation.
                  mid = count // 2
                  median = values[mid] if count % 2 else 0.5 * (values[mid - 1] + values[mid])
                  avrg = total / count
                  s = sum([(v - avrg)**2 for v in values])
                  stdev = math.sqrt(s / (count - 1)) if 1 < count else ''
                  stdevp = math.sqrt(s / count)

                  # Find mode.
                  mode, num = None, 0
                  for i, v in enumerate(sorted(histogram.keys())):
                      n = histogram[v]
                      if num < n:
                          mode, num = v, n
                      # Reserved: Set histogram elements
                      #feature.setAttribute('liststatisticscalculator.histogram{%d}.count' % i, n)
                      #feature.setAttribute('liststatisticscalculator.histogram{%d}.value' % i, v)

                  # Set statistics attributes.
                  feature.setAttribute('min.liststatisticscalculator', values[0])
                  feature.setAttribute('max.liststatisticscalculator', values[-1])
                  feature.setAttribute('median.liststatisticscalculator', median)
                  feature.setAttribute('count.liststatisticscalculator', count)
                  feature.setAttribute('sum.liststatisticscalculator', total)
                  feature.setAttribute('range.liststatisticscalculator', values[-1] - values[0])
                  feature.setAttribute('mean.liststatisticscalculator', avrg)
                  feature.setAttribute('stdev.liststatisticscalculator', stdev)
                  feature.setAttribute('stdevp.liststatisticscalculator', stdevp)
                  feature.setAttribute('mode.liststatisticscalculator', mode)

                  # Set flag.
                  feature.setAttribute('liststatisticscalculator.flag', 1)

              except Exception as ex:
                  feature.setAttribute('_liststats_error', '%s' % ex)
                  feature.setAttribute('liststatisticscalculator.flag', 0)

              self.pyoutput(feature)
    PYTHONSYMBOL = ListStatisticsCalculator
    -> Tester
Tester
    BOOL_OP = OR
    TEST_CLAUSE = TEST @Value(liststatisticscalculator.flag) = 1
    TEST_MODE = Automatic
    PASSED -> BulkAttributeRenamer
    FAILED -> BulkAttributeRemover_2
Note: Add common prefix
BulkAttributeRenamer
    ATTRCHOICE = Selected Attributes
    ATTRLIST = min.liststatisticscalculator max.liststatisticscalculator median.liststatisticscalculator count.liststatisticscalculator sum.liststatisticscalculator range.liststatisticscalculator mean.liststatisticscalculator stdev.liststatisticscalculator stdevp.liststatisticscalculator mode.liststatisticscalculator
    PATTERN_ACTION_DISP = Add String Prefix
    REPLACE_STR = $(PREFIX)
    -> BulkAttributeRenamer_2
Note: Remove extra suffix
BulkAttributeRenamer_2
    ATTRCHOICE = All Attributes
    CASE_DISP = yes
    PATTERN_ACTION_DISP = Remove Suffix String
    REPLACE_STR = .liststatisticscalculator
    -> BulkAttributeRemover
Note: Remove unnecessary attributes
BulkAttributeRemover
    ATTR_EXP = ^liststatisticscalculator
    -> Output (output)
Output (output)
BulkAttributeRemover_2
    ATTR_EXP = liststatisticscalculator
    -> AttributeExposer
Note: AttributeExposer [AttributeExposer] / Attributes To Expose: _liststats_error
AttributeExposer
    ATTR_LIST = _liststats_error
    -> <Rejected> (output)
<Rejected> (output)
