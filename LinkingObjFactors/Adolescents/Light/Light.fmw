FME workspace Light.fmw

Parameters:
- SourceDataset_SHAPEFILE = C:\Users\Sien Benoit\OneDrive - UGent\Werk_UGent\Doctoraat\Datasets_environment\lighting\GRB\Lighting_projected.shp   # Source Esri Shapefile(s)
- SourceDataset_SHAPEFILE_3 = C:\Users\Sien Benoit\OneDrive - UGent\Werk_UGent\Doctoraat\Datasets_routes\DataFietsbarometerVL_210402\06_LinkingObjFactors\Adolescents\dataset_adolescents_210402_08_total.shp   # Source Esri Shapefile(s)
- DestDataset_CSV2 = C:\Users\Sien Benoit\OneDrive - UGent\Werk_UGent\Doctoraat\Datasets_routes\DataFietsbarometerVL_210402\06_LinkingObjFactors\Adolescents\Light   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Light poles along roads in Flanders projected to Lambert72
Note: Calcutle the length in m of each route
Note: Create a buffer of 15 m around each route with no buffered area at the ends of the route.
Note: Count the number of lights in each buffer
Note: The attribute 'light' gives the number of lights per 100 m for each route.
Note: Select and rename the attributes and write to a csv file that can be joined to the original segments shapefile.
Lighting_projected (reader SHAPEFILE_1)
    attributes: OIDN number(15,0), UIDN number(15,0), VERSIE short, BEGINDATUM date, VERSDATUM date, TYPE short, LBLTYPE char(64), OPNDATUM date, BGNINV short, LBLBGNINV char(32)
    -> PointOnAreaOverlayer [POINT]
Note: Routes of the adolescents that need additional attributes
dataset_adolescents_210402_08_total (reader SHAPEFILE_2)
    attributes: student_id long, gender char(254), age long, class_nam char(254), class_grad long, school_id long, school_nam char(254), municipal char(254), postal_cod long, start_time char(254), end_time char(254), dur long, freq_sc double, rt_t_dist double, rt_t_dm char(254), rt_a_dist double, rt_a_infra char(254), rt_a_dm char(254), rt_a_cycl short, ov_saf_sc long, det_short short, det_least short, det_slow short, det_infra short, det_beau short, det_obs short, det_oths short, det_shop short, det_oth short, comp_nr long
    -> LengthCalculator

Bookmark: Calculate length
LengthCalculator
    DIM = 2
    LEN_ATTR = _length
    MULT = 1
    -> Bufferer

Bookmark: Buffer each segment
Bufferer
    ANGLE = 22.5
    CAP_STYLE = None
    CORNER_STYLE = Bevel
    MODE = AREA
    OFFSET = 15
    OFFSET_UNITS = NONE
    BUFFERED -> PointOnAreaOverlayer [AREA]

Bookmark: Count lights
PointOnAreaOverlayer
    DEAGGREGATE_INPUT = Yes
    OV_ATTR = _lights
    POLYS_FIRST = NO
    AREA -> AttributeCreator

Bookmark: Convert the attributes
AttributeCreator
    ATTR_TABLE = SET_TO _lights_per_100m = @mult(@div(@Value(_lights),@Value(_length)),100)
    -> AttributeManager

Bookmark: Write to csv
AttributeManager
    ATTR_TABLE:
      REMOVE _lights
      REMOVE _length
      RENAME_SET_VALUE _lights_per_100m > light
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
    -> Light (writer CSV2_1)
Light (writer CSV2_1)
    attributes: light string, student_id string
