FME workspace DiffRoutes.fmw

Parameters:
- SourceDataset_SHAPEFILE_3 = C:\Users\Sien Benoit\OneDrive - UGent\Werk_UGent\Doctoraat\Datasets_routes\DataFietsbarometerVL_210402\06_LinkingObjFactors\Adolescents\dataset_adolescents_210402_08_total.shp   # Source Esri Shapefile(s)
- SourceDataset_SHAPEFILE = C:\Users\Sien Benoit\OneDrive - UGent\Werk_UGent\Doctoraat\Datasets_environment\diffroutes\roads_vlaanderen_edges_2020_2021.shp   # Source Esri Shapefile(s)
- DestDataset_CSV2 = C:\Users\Sien Benoit\OneDrive - UGent\Werk_UGent\Doctoraat\Datasets_routes\DataFietsbarometerVL_210402\06_LinkingObjFactors\Adolescents\DiffRoutes   # Destination CSV (Comma Separated Value) Folder

Readers:
- SHAPEFILE_2: SHAPEFILE from $(SourceDataset_SHAPEFILE_3)
- SHAPEFILE_1: SHAPEFILE from $(SourceDataset_SHAPEFILE)

Writers:
- CSV2_1: CSV2 to $(DestDataset_CSV2)

Note: Road network of Flanders used in the Bike Barometer (2020-2021)
Note: Create a network from the lines.
Note: Extract the first and last vertex and connect them with a line to have from-to lines.
Note: Find the shortest path beween start and end point along the giiven network.
Note: Calculate the length of the original routes and of the shortest routes
Note: Bring the routes back together and calculate the difference in length between the original route and the shortest route.
Note: Remove unnecessary attributes and write to a csv file that can be joined to the original routes shapefile.
roads_vlaanderen_edges_2020_2021 (reader SHAPEFILE_1)
    attributes: gid long, osm_id char(10), name char(100), eenrichtin char(1), edge_id long, startpoint char(254), endpoint char(254), start_node long, end_node long
    -> NetworkTopologyCalculator [LINE]
Note: Routes of the adolescents that need additional attributes
dataset_adolescents_210402_08_total (reader SHAPEFILE_2)
    attributes: student_id long, gender char(254), age long, class_nam char(254), class_grad long, school_id long, school_nam char(254), municipal char(254), postal_cod long, start_time char(254), end_time char(254), dur long, freq_sc double, rt_t_dist double, rt_t_dm char(254), rt_a_dist double, rt_a_infra char(254), rt_a_dm char(254), rt_a_cycl short, ov_saf_sc long, det_short short, det_least short, det_slow short, det_infra short, det_beau short, det_obs short, det_oths short, det_shop short, det_oth short, comp_nr long
    -> CoordinateExtractor_start
    -> CoordinateExtractor_end
    -> LengthCalculator_2

Bookmark: Create network
NetworkTopologyCalculator
    NETWORK_ID_ATTR = _network_id
    NETWORK -> ShortestPathFinder [NETWORK]

Bookmark: Make lines from the start to the end point of every route
CoordinateExtractor_start
    IND = 0
    MODE = Specify Coordinate
    X_ATTR = _x
    Y_ATTR = _y
    Z_ATTR = _z
    -> VertexCreator
VertexCreator
    MEASURE_TYPE = Continuous
    MODE_NAME = Replace with Point
    XVAL = @Value(_x)
    YVAL = @Value(_y)
    -> LineBuilder
CoordinateExtractor_end
    IND = -1
    MODE = Specify Coordinate
    X_ATTR = _x
    Y_ATTR = _y
    Z_ATTR = _z
    -> VertexCreator_2
VertexCreator_2
    MEASURE_TYPE = Continuous
    MODE_NAME = Replace with Point
    XVAL = @Value(_x)
    YVAL = @Value(_y)
    -> LineBuilder
LineBuilder
    ACCUM_INPUT_ATTRS = Use Attributes From One Feature
    GROUP_BY = student_id
    REMOVE_DUPLICATES = No
    LINE -> ShortestPathFinder [FROM-TO]

Bookmark: Calculate length
LengthCalculator_2
    DIM = 2
    LEN_ATTR = length_route
    MULT = 1
    -> Aggregator
LengthCalculator
    DIM = 2
    LEN_ATTR = length_shortestpath
    MULT = 1
    -> Aggregator

Bookmark: Find the shortest path
ShortestPathFinder
    ALLOW_UTURNS = Yes
    REORDER_CHOICE = None
    SNAP_POINTS = Yes
    SNAP_TOLERANCE = 1
    WEIGHT_ATTR_CHOICE = By Length
    PATH -> LengthCalculator

Bookmark: Calculate length difference
Aggregator
    ACCUM_ATTRS_NAME = Use Attributes From One Feature
    AGGREGATE_TYPE = Homogeneous Collection (If Possible)
    GROUP_BY = student_id
    LIST_ATTRS_TO_INCLUDE = length_route length_shortestpath
    LIST_NAME = lengths
    MODE = Geometry - Assemble One Level
    SEP = ,
    AGGREGATE -> AttributeCreator
AttributeCreator
    ATTR_TABLE = SET_TO DiffRoutes = @Evaluate(@Value(lengths{1}.length_route)-@Value(lengths{0}.length_shortestpath))
    -> AttributeManager

Bookmark: Write to csv
AttributeManager
    ATTR_TABLE:
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
      REMOVE length_route
      REMOVE _x
      REMOVE _y
      REMOVE _z
      REMOVE length_shortestpath
      REMOVE lengths{}.length_route
      REMOVE lengths{}.length_shortestpath
    -> DiffRoutes (writer CSV2_1)
DiffRoutes (writer CSV2_1)
    attributes: DiffRoutes string, student_id string
