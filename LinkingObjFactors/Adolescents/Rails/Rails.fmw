FME workspace Rails.fmw

Parameters:
- SourceDataset_SHAPEFILE_3 = C:\Users\Sien Benoit\OneDrive - UGent\Werk_UGent\Doctoraat\Datasets_routes\DataFietsbarometerVL_210402\06_LinkingObjFactors\Adolescents\dataset_adolescents_210402_08_total.shp   # Source Esri Shapefile(s)
- SourceDataset_SHAPEFILE = C:\Users\Sien Benoit\OneDrive - UGent\Werk_UGent\Doctoraat\Datasets_environment\rails\GRB\Rails_projected.shp   # Source Esri Shapefile(s)
- SourceDataset_GEOTIFF = C:\Users\Sien Benoit\OneDrive - UGent\Werk_UGent\Doctoraat\Datasets_environment\height\DTM_Flanders.tif   # Source GeoTIFF File(s)
- DestDataset_CSV2 = C:\Users\Sien Benoit\OneDrive - UGent\Werk_UGent\Doctoraat\Datasets_routes\DataFietsbarometerVL_210402\06_LinkingObjFactors\Adolescents\Rails   # Destination CSV (Comma Separated Value) Folder

Readers:
- SHAPEFILE_2: SHAPEFILE from $(SourceDataset_SHAPEFILE_3)
- SHAPEFILE_1: SHAPEFILE from $(SourceDataset_SHAPEFILE)
- GEOTIFF_1: GEOTIFF from $(SourceDataset_GEOTIFF)

Writers:
- CSV2_1: CSV2 to $(DestDataset_CSV2)

Note: Adolescents' routes dataset that needs additional new attributes
dataset_adolescents_210402_08_total (reader SHAPEFILE_2)
    attributes: student_id long, gender char(254), age long, class_nam char(254), class_grad long, school_id long, school_nam char(254), municipal char(254), postal_cod long, start_time char(254), end_time char(254), dur long, freq_sc double, rt_t_dist double, rt_t_dm char(254), rt_a_dist double, rt_a_infra char(254), rt_a_dm char(254), rt_a_cycl short, ov_saf_sc long, det_short short, det_least short, det_slow short, det_infra short, det_beau short, det_obs short, det_oths short, det_shop short, det_oth short, comp_nr long
    -> AttributeManager_5
    -> FeatureJoiner_3 [LEFT]
Note: Train and tram rails in Flanders (also unused rails) mapped in the GRB as wrl
Note: Remove unnecessary attributes
Note: Intersect the rails and the routes and ignore intersections between features in the same feature class. / Extract the lines of the rails that are intersected
Note: Keep only the first 10 m of the intersected rail
Note: First, add a point at 75 m to the north of the intersection point to create a line. Second, rotate this line based on the horizontal angle of the intersected rail. Finally, extract the end point of this rotated line.
Note: Calculate the height of the intersected points and the points at 75 m. Remove unnecessary attributes.
Note: Match points that belong together. If the difference in height is more than 2 m, there is no real intersection (but possibly a bridge or tunnel). Else, the intersection is real.
Note: Aggregate the records per student id and sum the number of real rail intersections.
Note: Join the points to the original routes. Routes that did not have an intersection get a value of 0 for the attribute 'rails'.
Note: Write to a csv file that can be joined to the original routes shapefile.
Rails_projected (reader SHAPEFILE_1)
    attributes: OIDN number(15,0), UIDN number(15,0), VERSIE short, BEGINDATUM date, VERSDATUM date, BHRDR short, LBLBHRDR char(32), LIJNNR char(10), OPNDATUM date, BGNINV short, LBLBGNINV char(32), LENGTE double
    -> AttributeManager
Note: Digital Terrain Model of (part of) Flanders
GEOTIFF (reader GEOTIFF_1)
    -> PointOnRasterValueExtractor [RASTER]
    -> PointOnRasterValueExtractor_2 [RASTER]

Bookmark: Keep only the OID
AttributeManager_5
    ATTR_TABLE:
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
    -> Intersector
AttributeManager
    ATTR_TABLE:
      REMOVE UIDN
      REMOVE VERSIE
      REMOVE BEGINDATUM
      REMOVE VERSDATUM
      REMOVE BHRDR
      REMOVE LBLBHRDR
      REMOVE LIJNNR
      REMOVE OPNDATUM
      REMOVE BGNINV
      REMOVE LBLBGNINV
      REMOVE LENGTE
    -> Intersector

Bookmark: Intersect
Intersector
    ATTRS_ACCUM_MODE = Merge Attributes
    CLEANING_TOLERANCE = Automatic
    DEAGGREGATE_INPUT = Yes
    DUPLICATE_Z_NODES = No
    GENERATE_LIST_DROP = NO
    MEASURE_TYPE = Continuous
    NODE_NUM_ATTR = _node_number
    OV_ATTR = _overlaps
    PERFORM_SELF_INTERSECTION = Yes
    SEG_ATTR = _segments
    SEPARATE_COLLINEAR_SEGMENTS = Yes
    INTERSECTED -> Tester_2
    NODE -> Tester
Tester_2
    BOOL_OP = COMPOSITE
    COMPOSITE_TEST = 1 AND 2
    TEST_CLAUSE:
      TEST @Value(_segments) > 1
      TEST OIDN ATTRIBUTE_HAS_A_VALUE ""
    TEST_MODE = TEST
    PASSED -> PointOnLineOverlayer [LINE]
Tester
    BOOL_OP = COMPOSITE
    COMPOSITE_TEST = 1 AND 2
    TEST_CLAUSE:
      TEST student_id ATTRIBUTE_HAS_A_VALUE ""
      TEST OIDN ATTRIBUTE_HAS_A_VALUE ""
    TEST_MODE = TEST
    PASSED -> PointOnRasterValueExtractor [POINT]
    PASSED -> CoordinateExtractor
    PASSED -> PointOnLineOverlayer [POINT]
PointOnLineOverlayer
    ATTR_ACCUM_MODE = Prefix Incoming
    DEAGGREGATE_INPUT = Yes
    INCOMING_PREFIX = pre
    MEASURE_TYPE = Continuous
    MERGE_MEASURES = Yes
    OV_ATTR = _overlaps
    TOLERANCE = 0.1
    LINE -> Tester_3
Tester_3
    BOOL_OP = OR
    COMPOSITE_TEST = 1
    TEST_CLAUSE = TEST pre_node_number ATTRIBUTE_HAS_A_VALUE ""
    TEST_MODE = TEST
    PASSED -> Snipper

Bookmark: Snip the intersected rail lines
Snipper
    DEAGGREGATE_INPUT = YES
    ENDLOCATIONATTR = 10
    MEASUREMENTTYPE = 2D
    SNIPMODE = Distance (Value)
    STARTLOCATIONATTR = 0
    -> HorizontalAngleCalculator

Bookmark: Create a point at 75 m perpendicular to the snipped intersected rail
HorizontalAngleCalculator
    ANGLE_TYPE = Feature
    UNIT_OUTPUT = DEG
    -> DuplicateFilter
DuplicateFilter
    INPUT_ORDERED_CHOICE = No
    KEYATTR = pre_node_number
    UNIQUE -> FeatureJoiner_2 [RIGHT]
CoordinateExtractor
    IND = 0
    MODE = Specify Coordinate
    X_ATTR = _xco
    Y_ATTR = _yco
    Z_ATTR = _zco
    -> VertexCreator
VertexCreator
    MEASURE_TYPE = Continuous
    MISSING_VAL_MODE = Compute
    MODE_NAME = Add Point
    XVAL = @Value(_xco)
    YVAL = @Value(_yco) + 75
    -> FeatureJoiner_2 [LEFT]
FeatureJoiner_2
    ATTR_CONFLICT_RES = Use Left
    GEOMETRY_HANDLING = Use Left
    JOIN_KEYS = _node_number pre_node_number AUTO
    JOIN_MODE = Left
    JOINED -> Rotator
Rotator
    ANGLE = @Value(_angle)
    XORIG = @Value(_xco)
    YORIG = @Value(_yco)
    ROTATED -> CoordinateExtractor_2
CoordinateExtractor_2
    IND = -1
    MODE = Specify Coordinate
    X_ATTR = _xend
    Y_ATTR = _yend
    Z_ATTR = _zend
    -> VertexCreator_2
VertexCreator_2
    MEASURE_TYPE = Continuous
    MODE_NAME = Replace with Point
    XVAL = @Value(_xend)
    YVAL = @Value(_yend)
    -> PointOnRasterValueExtractor_2 [POINT]

Bookmark: Find the height
PointOnRasterValueExtractor_2
    INTERPOLATION_TYPE_NAME = Nearest Neighbor
    POINT -> AttributeManager_2
AttributeManager_2
    ATTR_TABLE:
      REMOVE fme_basename
      REMOVE _xco
      REMOVE _yco
      REMOVE _zco
      REMOVE _azimuth
      REMOVE _X
      REMOVE _Y
      REMOVE _angle
      REMOVE preOIDN
      REMOVE _overlaps
      REMOVE _segments
      REMOVE _creation_instance
      REMOVE _x
      REMOVE _y
      REMOVE _z
      REMOVE _xEnd
      REMOVE _yEnd
      REMOVE _zEnd
      REMOVE _xend
      REMOVE _yend
      REMOVE _zend
      RENAME_SET_VALUE _band{}.value > _band_a{}.value
      REMOVE _band{}.palette{}.value
      REMOVE student_id
    -> FeatureJoiner [RIGHT]
PointOnRasterValueExtractor
    INTERPOLATION_TYPE_NAME = Nearest Neighbor
    POINT -> AttributeManager_3
AttributeManager_3
    ATTR_TABLE:
      REMOVE fme_basename
      REMOVE OIDN
      RENAME_SET_VALUE _band{}.value > _band_b{}.value
      REMOVE _band{}.palette{}.value
    -> FeatureJoiner [LEFT]

Bookmark: Find points where rails intersect
FeatureJoiner
    ATTR_CONFLICT_RES = Use Left
    GEOMETRY_HANDLING = Use Left
    JOIN_KEYS = _node_number _node_number AUTO
    JOIN_MODE = Inner
    JOINED -> AttributeCreator
AttributeCreator
    ATTR_TABLE = SET_TO rails = FME_CONDITIONAL:DEFAULT_VALUE'@Evaluate(1)'BOOL_OP;OR;COMPOSITE_TEST;1;NUM_TEST @abs(@Value(_band_a{0}.value)-@Value(_band_b{0}.value)) > 2'@Evaluate(0)'FME_NUM_CONDITIONS2___
    -> Aggregator

Bookmark: Sum the rails intersections
Aggregator
    ACCUM_ATTRS_NAME = Use Attributes From One Feature
    AGGREGATE_TYPE = Homogeneous Collection (If Possible)
    GROUP_BY = student_id
    MODE = Geometry - Assemble One Level
    SEP = ,
    SUM = rails
    AGGREGATE -> FeatureJoiner_3 [RIGHT]

Bookmark: Join points and routes
FeatureJoiner_3
    ATTR_CONFLICT_RES = Use Left
    GEOMETRY_HANDLING = Use Left
    JOIN_KEYS = student_id student_id AUTO
    JOIN_MODE = Left
    JOINED -> AttributeManager_4
AttributeManager_4
    ATTR_TABLE:
      SET_TO rails = FME_CONDITIONAL:DEFAULT_VALUE'_FME_NO_OP_'BOOL_OP;OR;COMPOSITE_TEST;1;TEST rails ATTRIBUTE_VALUE_NULL _FME_BLANK_STRING_'@Evaluate(0)'FME_NUM_CONDITIONS2___
      REMOVE _node_number
      REMOVE _band_b{}.value
      REMOVE OIDN
      REMOVE pre_node_number
      REMOVE _band_a{}.value
      REMOVE prestudent_id
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
    -> Rails (writer CSV2_1)

Bookmark: Write to csv
Rails (writer CSV2_1)
    attributes: rails string, student_id string
