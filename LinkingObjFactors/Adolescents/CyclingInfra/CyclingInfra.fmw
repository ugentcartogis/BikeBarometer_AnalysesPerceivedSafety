FME workspace CyclingInfra.fmw

Parameters:
- SourceDataset_SHAPEFILE = C:\Users\Sien Benoit\OneDrive - UGent\Werk_UGent\Doctoraat\Datasets_environment\cyclinginfra\dataset_segments_210402_08_infra.shp   # Source Esri Shapefile(s)
- SourceDataset_SHAPEFILE_3 = C:\Users\Sien Benoit\OneDrive - UGent\Werk_UGent\Doctoraat\Datasets_routes\DataFietsbarometerVL_210402\06_LinkingObjFactors\Adolescents\dataset_adolescents_210402_08_assessed.shp   # Source Esri Shapefile(s)
- DestDataset_CSV2 = C:\Users\Sien Benoit\OneDrive - UGent\Werk_UGent\Doctoraat\Datasets_routes\DataFietsbarometerVL_210402\06_LinkingObjFactors\Adolescents\CyclingInfra   # Destination CSV (Comma Separated Value) Folder

Readers:
- SHAPEFILE_1: SHAPEFILE from $(SourceDataset_SHAPEFILE)
- SHAPEFILE_2: SHAPEFILE from $(SourceDataset_SHAPEFILE_3)

Writers:
- CSV2_1: CSV2 to $(DestDataset_CSV2)

Note: Segments of the Bike Barometer with the most assigned cycling infrastructure.
Note: Remove unnecessary attributes.
Note: Find all segments of which each route is composed by intersecting the lines and extracting all students on each segment, and removing duplicate rows.
Note: Filter on each cycling infrastructure type and calculate the length of the segments of each type.
Note: Remove unnecessary attributes. Aggregate the segments of each student and sum the lengths of each cycling infrastructure type for each student.
Note: Calculate the length of the complete assessed route and use this to calculate the proportion of each cycling infrastructure type for each route.
Note: Remove unnecessary attributes and write the data to a csv file that can be joined to the original shapefile of the routes.
dataset_segments_210402_08_infra (reader SHAPEFILE_1)
    attributes: segment_id long, mode char(254)
    -> LineOnLineOverlayer [LINE]
Note: Routes of the adolescents that need additional attributes. Assessed routes and not the total routes!
dataset_adolescents_210402_08_assessed (reader SHAPEFILE_2)
    attributes: student_id long, gender char(254), age long, class_nam char(254), class_grad long, school_id long, school_nam char(254), municipal char(254), postal_cod long, start_time char(254), end_time char(254), dur long, freq_sc double, rt_t_dist double, rt_t_dm char(254), rt_a_dist double, rt_a_infra char(254), rt_a_dm char(254), rt_a_cycl short, ov_saf_sc long, det_short short, det_least short, det_slow short, det_infra short, det_beau short, det_obs short, det_oths short, det_shop short, det_oth short, comp_nr long
    -> AttributeManager

Bookmark: Remove attributes
AttributeManager
    ATTR_TABLE:
      REMOVE gender
      REMOVE age
      REMOVE class_nam
      REMOVE class_grad
      REMOVE school_id
      REMOVE school_nam
      REMOVE municipal
      REMOVE postal_cod
      REMOVE start_time
      REMOVE end_time
      REMOVE dur
      REMOVE freq_sc
      REMOVE rt_t_dist
      REMOVE rt_t_dm
      REMOVE rt_a_dist
      REMOVE rt_a_infra
      REMOVE rt_a_dm
      REMOVE rt_a_cycl
      REMOVE ov_saf_sc
      REMOVE det_short
      REMOVE det_least
      REMOVE det_slow
      REMOVE det_infra
      REMOVE det_beau
      REMOVE det_obs
      REMOVE det_oths
      REMOVE det_shop
      REMOVE det_oth
      REMOVE comp_nr
    -> LineOnLineOverlayer [LINE]

Bookmark: Find the cycling infrastructure of each segment of each route.
LineOnLineOverlayer
    ATTRS_ACCUM_MODE = Merge Attributes
    CLEANING_TOLERANCE = Automatic
    DEAGGREGATE_INPUT = Yes
    GENERATE_LIST_DROP = YES
    LIST_ATTRS_TO_INCLUDE = student_id
    LIST_NAME = list_
    OV_ATTR = _overlaps
    SEPARATE_COLLINEAR_SEGMENTS = No
    LINE -> ListExploder
ListExploder
    ATTR_ACCUM_MODE = Merge List Attributes
    ATTR_CONFLICT_RES = Use List Attribute Values
    INDEX_ATTR = _element_index
    LIST_ATTR = list_{}
    ELEMENTS -> DuplicateFilter
DuplicateFilter
    INPUT_ORDERED_CHOICE = No
    KEYATTR = segment_id student_id
    UNIQUE -> Tester_bike_suggestion
    UNIQUE -> Tester_non-sep_bike_lane
    UNIQUE -> Tester_other
    UNIQUE -> Tester_forbidden
    UNIQUE -> Tester_bike_highw
    UNIQUE -> Tester_pedestrian
    UNIQUE -> Tester_bike_street_no_cars
    UNIQUE -> Tester_no_cycling_infra
    UNIQUE -> Tester_sep_bike_lane
    UNIQUE -> Tester_bike_street

Bookmark: Find the length of each cycling infrastructure type per segment of a route.
Tester_no_cycling_infra
    BOOL_OP = OR
    COMPOSITE_TEST = 1
    TEST_CLAUSE = TEST @Value(mode) = no cycling infrastructure
    TEST_MODE = TEST
    PASSED -> LengthCalculator_2
LengthCalculator_2
    DIM = 2
    LEN_ATTR = length_nocyclinginfra
    MULT = 1
    -> AttributeManager_2
Tester_sep_bike_lane
    BOOL_OP = OR
    COMPOSITE_TEST = 1
    TEST_CLAUSE = TEST @Value(mode) = separated bike lane
    TEST_MODE = TEST
    PASSED -> LengthCalculator_3
LengthCalculator_3
    DIM = 2
    LEN_ATTR = length_sep_bike_lane
    MULT = 1
    -> AttributeManager_2
Tester_non-sep_bike_lane
    BOOL_OP = OR
    COMPOSITE_TEST = 1
    TEST_CLAUSE = TEST @Value(mode) = non-separated bike lane
    TEST_MODE = TEST
    PASSED -> LengthCalculator_4
LengthCalculator_4
    DIM = 2
    LEN_ATTR = length_non-sep_bike_lane
    MULT = 1
    -> AttributeManager_2
Tester_bike_street
    BOOL_OP = OR
    COMPOSITE_TEST = 1
    TEST_CLAUSE = TEST @Value(mode) = bike street
    TEST_MODE = TEST
    PASSED -> LengthCalculator_5
LengthCalculator_5
    DIM = 2
    LEN_ATTR = length_bike_street
    MULT = 1
    -> AttributeManager_2
Tester_bike_highw
    BOOL_OP = OR
    COMPOSITE_TEST = 1
    TEST_CLAUSE = TEST @Value(mode) = bike highway
    TEST_MODE = TEST
    PASSED -> LengthCalculator_6
LengthCalculator_6
    DIM = 2
    LEN_ATTR = length_bike_highw
    MULT = 1
    -> AttributeManager_2
Tester_bike_street_no_cars
    BOOL_OP = OR
    COMPOSITE_TEST = 1
    TEST_CLAUSE = TEST @Value(mode) = bike street or lane without cars
    TEST_MODE = TEST
    PASSED -> LengthCalculator_7
LengthCalculator_7
    DIM = 2
    LEN_ATTR = length_bike_street_no_cars
    MULT = 1
    -> AttributeManager_2
Tester_bike_suggestion
    BOOL_OP = OR
    COMPOSITE_TEST = 1
    TEST_CLAUSE = TEST @Value(mode) = bike suggestion lane
    TEST_MODE = TEST
    PASSED -> LengthCalculator_8
LengthCalculator_8
    DIM = 2
    LEN_ATTR = length_bike_suggestion
    MULT = 1
    -> AttributeManager_2
Tester_forbidden
    BOOL_OP = OR
    COMPOSITE_TEST = 1
    TEST_CLAUSE = TEST @Value(mode) = forbidden for cyclists
    TEST_MODE = TEST
    PASSED -> LengthCalculator_9
LengthCalculator_9
    DIM = 2
    LEN_ATTR = length_forbidden
    MULT = 1
    -> AttributeManager_2
Tester_other
    BOOL_OP = OR
    COMPOSITE_TEST = 1
    TEST_CLAUSE = TEST @Value(mode) = other
    TEST_MODE = TEST
    PASSED -> LengthCalculator_10
LengthCalculator_10
    DIM = 2
    LEN_ATTR = length_other
    MULT = 1
    -> AttributeManager_2
Tester_pedestrian
    BOOL_OP = OR
    COMPOSITE_TEST = 1
    TEST_CLAUSE = TEST @Value(mode) = pedestrian zone or street
    TEST_MODE = TEST
    PASSED -> LengthCalculator_11
LengthCalculator_11
    DIM = 2
    LEN_ATTR = length_pedestrian
    MULT = 1
    -> AttributeManager_2

Bookmark: Merge all segments back to the routes.
AttributeManager_2
    ATTR_TABLE:
      REMOVE segment_id
      REMOVE mode
      REMOVE _overlaps
      REMOVE direction
      REMOVE _element_index
    -> Aggregator
Aggregator
    ACCUM_ATTRS_NAME = Use Attributes From One Feature
    AGGREGATE_TYPE = Homogeneous Collection (If Possible)
    GROUP_BY = student_id
    MODE = Geometry - Assemble One Level
    SEP = ,
    SUM = length_non-sep_bike_lane length_bike_street_no_cars length_forbidden length_nocyclinginfra length_sep_bike_lane length_bike_suggestion length_bike_street length_other length_bike_highw
    AGGREGATE -> LengthCalculator

Bookmark: Calculate the proportion of each cycling infrastructure type.
LengthCalculator
    DIM = 2
    LEN_ATTR = length_assessed
    MULT = 1
    -> AttributeCreator
AttributeCreator
    ATTR_TABLE:
      SET_TO no_cycling_infra = @Evaluate(@Value(length_nocyclinginfra)/@Value(length_assessed))
      SET_TO bike_suggestion_lane = @Evaluate(@Value(length_bike_suggestion)/@Value(length_assessed))
      SET_TO non_sep_bike_lane = @Evaluate(@Value(length_non-sep_bike_lane)/@Value(length_assessed))
      SET_TO sep_bike_lane = @Evaluate(@Value(length_sep_bike_lane)/@Value(length_assessed))
      SET_TO bike_street = @Evaluate(@Value(length_bike_street)/@Value(length_assessed))
      SET_TO bike_street_no_cars = @Evaluate(@Value(length_bike_street_no_cars)/@Value(length_assessed))
      SET_TO bike_highway = @Evaluate(@Value(length_bike_highw)/@Value(length_assessed))
      SET_TO pedestrian_lane = @Evaluate(@Value(length_pedestrian)/@Value(length_assessed))
      SET_TO forbidden_for_cyclists = @Evaluate(@Value(length_forbidden)/@Value(length_assessed))
      SET_TO other_cycling_infra = @Evaluate(@Value(length_other)/@Value(length_assessed))
    -> AttributeManager_3

Bookmark: Write to csv.
AttributeManager_3
    ATTR_TABLE:
      REMOVE length_sep_bike_lane
      REMOVE length_nocyclinginfra
      REMOVE length_bike_street_no_cars
      REMOVE length_bike_suggestion
      REMOVE length_bike_street
      REMOVE length_bike_highw
      REMOVE length_other
      REMOVE length_non-sep_bike_lane
      REMOVE length_forbidden
      REMOVE length_pedestrian
    -> CyclingInfra (writer CSV2_1)
CyclingInfra (writer CSV2_1)
    attributes: student_id string, no_cycling_infra string, bike_suggestion_lane string, non_sep_bike_lane string, sep_bike_lane string, bike_street string, bike_street_no_cars string, bike_highway string, pedestrian_lane string, forbidden_for_cyclists string, other_cycling_infra string, length_assessed string
